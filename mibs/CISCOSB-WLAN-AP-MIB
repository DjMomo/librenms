-- *****************************************************************
-- ciscosbWLANAP.mx
--   
-- Copyright (c) 2005-2006, 2011 by Cisco Systems Inc.

--   
-- Cisco Wireless Access Point MIB
-- This SNMP Management Information Specification
-- embodies Cisco Corporation's confidential and proprietary
-- intellectual property. Cisco Corporation retains all title
-- and ownership in the Specification including any revisions.
--
-- This Specification is supplied "AS IS", Cisco Corporation
-- makes no warranty, either expressed or implied,
-- as to the use, operation, condition, or performance of the
-- Specification.
-- *****************************************************************

CISCO-WLAN-ACCESS-POINT-MIB DEFINITIONS ::= BEGIN

IMPORTS
    MODULE-IDENTITY, OBJECT-TYPE, 
    Integer32                              FROM SNMPv2-SMI
    DisplayString, TruthValue, RowStatus,
    MacAddress, TEXTUAL-CONVENTION         FROM SNMPv2-TC
    InetAddressType, InetAddress           FROM INET-ADDRESS-MIB
    wap002                                 FROM CISCO-WLAN-ACCESS-POINT-REF-MIB
    InterfaceIndex                         FROM IF-MIB
    SnmpAdminString                        FROM SNMP-FRAMEWORK-MIB
    MODULE-COMPLIANCE, OBJECT-GROUP        FROM SNMPv2-CONF;

    ciscosbWLANAP MODULE-IDENTITY
        LAST-UPDATED "201105230000Z" -- 23 May 2011 12:00:00 GMT
        ORGANIZATION "Cisco Small Business"
        CONTACT-INFO
          "Postal:               170 West Tasman Drive
                                 San Jose, CA 95134-1706
                                 USA
          Website: Cisco Small Business Home http://www.cisco.com/smb
          <http://www.cisco.com/smb>, Cisco Small Business Support Community
          http://www.cisco.com/go/smallbizsupport"
        DESCRIPTION
          "Private MIB for Cisco SB Wireless Access Points."

        -- Revision history.
        REVISION
          "201105230000Z" -- 23 May 2011 12:00:00 GMT
        DESCRIPTION
          "Initial release."

    ::= { wap002 1 }

-- *****************************************************************
-- TEXTUAL CONVENTIONS
-- *****************************************************************

ApRadioId ::= TEXTUAL-CONVENTION
    DISPLAY-HINT "32a"
    STATUS       current
    DESCRIPTION
	"A short string that uniquely identifies a radio."
    SYNTAX OCTET STRING (SIZE(0..32))

ApBssId ::= TEXTUAL-CONVENTION
    DISPLAY-HINT "1x:"
    STATUS       current
    DESCRIPTION
	"A short string that uniquely idenfities a BSS."
    SYNTAX       OCTET STRING (SIZE(0..64))

ApSsid ::= TEXTUAL-CONVENTION
    DISPLAY-HINT "32a"
    STATUS       current
    DESCRIPTION
	"An SSID represented as an octet string."
    SYNTAX       OCTET STRING

ApAntennaSel ::=TEXTUAL-CONVENTION
    STATUS       current
    DESCRIPTION  
	"The integer representation of Antenna numbers"
    SYNTAX      INTEGER {
                    leftAndright(1),
                    leftAndmiddle(2),
                    middleAndright(3)
                }

TspecSuppAC ::= TEXTUAL-CONVENTION
    STATUS        current
    DESCRIPTION
        "Access category (AC) used for TSPEC.  Only those ACs that 
         support mandatory admission control are listed here."
    SYNTAX      INTEGER {
                    voice(0),
                    video(1)
                }

  ApLogSeverity ::= TEXTUAL-CONVENTION
        STATUS       current
        DESCRIPTION
            "Severity code used in determining the Log Priority value."
        REFERENCE
            "RFC3164 - 4.1.1: Table 2"
        SYNTAX  INTEGER {
                none(-1),       -- Invalid severity level.
		emergency(0),   -- System is unusable. System failure has occurred.
        	alert(1),       -- Action must be taken immediately. Unrecoverable
                	        -- failure of a component. System failure likely.
		critical(2),    -- Critical conditions. Recoverable failure of a                                
                       	        -- Component that may lead to system failure.
        	error(3),       -- Error conditions. Recoverable failure of a component.
    	        warning(4),     -- Warning conditions.  
   	        notice(5),      -- Normal but significant conditions.
       	        informational(6), -- Informational messages.
        	debug(7)        -- Debug-level messages.
        }


apGlobalConfig            OBJECT IDENTIFIER ::= { ciscosbWLANAP 1 }
  apSysConfig             OBJECT IDENTIFIER ::= { apGlobalConfig 1 }
  i802System              OBJECT IDENTIFIER ::= { apGlobalConfig 2 }    
--  managedAPConfig         OBJECT IDENTIFIER ::= { apGlobalConfig 3 } this OID is obsolete
  apConfigSupplicant      OBJECT IDENTIFIER ::= { apGlobalConfig 4 }
  apSupplicantCertificateUpload      OBJECT IDENTIFIER ::= { apConfigSupplicant 7 }
  apHost                  OBJECT IDENTIFIER ::= { apGlobalConfig 5 }
  apMgmtAccess            OBJECT IDENTIFIER ::= { apGlobalConfig 6 }
  apMgmtConfig            OBJECT IDENTIFIER ::= { apGlobalConfig 7 }
  apGlobalRadiusServer    OBJECT IDENTIFIER ::= { apGlobalConfig 8 }        
  apStaticIpRoute         OBJECT IDENTIFIER ::= { apGlobalConfig 9 }        
  apStaticIPv6Route       OBJECT IDENTIFIER ::= { apGlobalConfig 10 }
  apBridgeConfig          OBJECT IDENTIFIER ::= { apGlobalConfig 11 }

  apCodeDownload          OBJECT IDENTIFIER ::= { ciscosbWLANAP 2 }
  apFirmwareUpgrade       OBJECT IDENTIFIER ::= { apCodeDownload 3 }
  apFileTransfer          OBJECT IDENTIFIER ::= { apCodeDownload 4 }
  apLog                   OBJECT IDENTIFIER ::= { ciscosbWLANAP 3 }
  apLogConfig             OBJECT IDENTIFIER ::= { apLog 1 }

  apVap                   OBJECT IDENTIFIER ::= { ciscosbWLANAP 4 }

  apIfConfig              OBJECT IDENTIFIER ::= { ciscosbWLANAP 5 }

  apRadioBss              OBJECT IDENTIFIER ::= { ciscosbWLANAP 6 }

  apAssociation           OBJECT IDENTIFIER ::= { ciscosbWLANAP 7 }

  apDetectedAp            OBJECT IDENTIFIER ::= { ciscosbWLANAP 8 }
    apDetectedRogueApTrap OBJECT IDENTIFIER ::= { apDetectedAp 2 }

  apRadioRates            OBJECT IDENTIFIER ::= { ciscosbWLANAP 9 }

  apQos                   OBJECT IDENTIFIER ::= { ciscosbWLANAP 10 }
  wlanAPConformance       OBJECT IDENTIFIER ::= { ciscosbWLANAP 11 }
  apTspecTables           OBJECT IDENTIFIER ::= { ciscosbWLANAP 12 }
  apTspec                 OBJECT IDENTIFIER ::= { apTspecTables 2}
  apTspecConfig           OBJECT IDENTIFIER ::= { apTspecTables 5}

  apPacketCapture         OBJECT IDENTIFIER ::= { ciscosbWLANAP 13 }

  apPacketCaptureStatusInfo  OBJECT IDENTIFIER ::= { apPacketCapture 1}
  apPacketCaptureConfig      OBJECT IDENTIFIER ::= { apPacketCapture 2}
  apPacketCaptureFile        OBJECT IDENTIFIER ::= { apPacketCapture 3}
  apPacketCaptureRemote      OBJECT IDENTIFIER ::= { apPacketCapture 4}

apDateTime                  OBJECT IDENTIFIER ::= { ciscosbWLANAP 15 }
  apEmailAlert                OBJECT IDENTIFIER ::= { ciscosbWLANAP 16 }
  apEmailAlertConfig          OBJECT IDENTIFIER ::= { apEmailAlert 1}
  apEmailAlertStatus          OBJECT IDENTIFIER ::= { apEmailAlert 2}

  apScheduler                 OBJECT IDENTIFIER ::= { ciscosbWLANAP 17 }
  apSchedulerConfig           OBJECT IDENTIFIER ::= { apScheduler 1}
  apSchedulerProfile          OBJECT IDENTIFIER ::= { apScheduler 2}
  apWPS                OBJECT IDENTIFIER ::= { ciscosbWLANAP 18 }
  apWPSGlobal          OBJECT IDENTIFIER ::= { apWPS 1}
  apWgBridge                      OBJECT IDENTIFIER ::= { ciscosbWLANAP 19 }
  apWgBridgeEntry                      OBJECT IDENTIFIER ::= { apWgBridge 1 }
  apWgBridgeUpstrmEntry                      OBJECT IDENTIFIER ::= { apWgBridge 2}
  apWgBridgeDwstrmEntry                      OBJECT IDENTIFIER ::= { apWgBridge 3}
--******************************************************************
--  apSysConfig         OBJECT IDENTIFIER ::= { apGlobalConfig 1 }
--******************************************************************

apSysConfPasswd         OBJECT-TYPE
        SYNTAX          DisplayString(SIZE(1..80))
        MAX-ACCESS      read-write
        STATUS          current
        DESCRIPTION
        "Configures administrative password to access CLI and Web User
        Interface. Administrator password contains characters from at least 3 
        of the following 4 categories: Uppercase letters, Lowercase letters, 
        Numbers, and Special characters available on a standard keyboard.
        The range of the password length should be compliant with the configured 
        minimum-password-length and maximum-password-length.
        The read of this parameter will return null string."
        ::= { apSysConfig 1 }

apSysConfModel   OBJECT-TYPE
        SYNTAX DisplayString
        MAX-ACCESS read-only
        STATUS current
        DESCRIPTION
                "Hardware model of this system."
        ::= { apSysConfig 2 }

apSysConfVersion   OBJECT-TYPE
        SYNTAX DisplayString
        MAX-ACCESS read-only
        STATUS current
        DESCRIPTION
        "Version number of the software running on the AP."
        ::= { apSysConfig 3 }

apSysConfPlatform   OBJECT-TYPE
        SYNTAX DisplayString
        MAX-ACCESS read-only
        STATUS current
        DESCRIPTION
                "Hardware platform for the AP."
        ::= { apSysConfig 4 }

apSysCountryCode  OBJECT-TYPE
        SYNTAX          DisplayString(SIZE(2))
        MAX-ACCESS      read-only
        STATUS          current
        DESCRIPTION
        "Country within which AP is operating."
        ::= { apSysConfig 5 }
     
apSysConfBaseMac  OBJECT-TYPE
        SYNTAX MacAddress
        MAX-ACCESS read-only
        STATUS current
        DESCRIPTION
        "Base MAC address of the AP. The Lowest MAC Address
        from a 24-address block."
        ::= { apSysConfig 6 }

apSysConfSerialNumber  OBJECT-TYPE
        SYNTAX DisplayString
        MAX-ACCESS read-only
        STATUS current
        DESCRIPTION
                "Serial Number of the AP."
        ::= { apSysConfig 7 }

apSysConfCountryCodeIsConfigurable  OBJECT-TYPE
        SYNTAX DisplayString 
        MAX-ACCESS read-only
        STATUS current
        DESCRIPTION
        "Indicates whether country code is configurable on this AP."
        ::= { apSysConfig 8 }

apSysConfPasswdComplexitySupport  OBJECT-TYPE
	SYNTAX	TruthValue
	MAX-ACCESS read-write
	STATUS current
	DESCRIPTION
	"Enable/Disable the enforecement of minimum complexity of User Passwords."
	DEFVAL              { true } 
	::= { apSysConfig 9} 	 	

apSysConfPasswdMinCharClass  OBJECT-TYPE
        SYNTAX  Integer32 (1..4)
        MAX-ACCESS read-write
        STATUS current
        DESCRIPTION
        "Indicates the minimum character class of User Passwords."
        ::= { apSysConfig 10}

apSysConfPasswdMinLength  OBJECT-TYPE
        SYNTAX  Integer32 (0..32)
        MAX-ACCESS read-write
        STATUS current
        DESCRIPTION
        "Indicates how much minimum length of User Passwords is mandatory, if Minimum Length constraint is enabled."
        ::= { apSysConfig 12}

apSysConfPasswdMaxLength  OBJECT-TYPE
        SYNTAX  Integer32 (64..80)
        MAX-ACCESS read-write
        STATUS current
        DESCRIPTION
        "Indicates how much maximum length of User Passwords is allowed."
        ::= { apSysConfig 13}
apSysConfPasswdAgingSupport  OBJECT-TYPE
        SYNTAX  TruthValue
        MAX-ACCESS read-write
        STATUS current
        DESCRIPTION
        "Enable/Disable the enforcement of aging feature of User Passwords."
	DEFVAL              { true }
        ::= { apSysConfig 14}
apSysConfPasswdAgingTime   OBJECT-TYPE
        SYNTAX  Integer32 (1..365)
        MAX-ACCESS read-write
        STATUS current
        DESCRIPTION
        "Indicates in how many days, User Passwords will age, if Password Aging constraint is enabled. "
        ::= { apSysConfig 15}
apSysConfPasswdDiffFrmCurr  OBJECT-TYPE
        SYNTAX  TruthValue
        MAX-ACCESS read-write
        STATUS current
        DESCRIPTION
        "Enable/Disable to allow/prevent repetition of same User Password as new User Password. "
	DEFVAL              { true }
        ::= { apSysConfig 16}
apSysConfWpaPskComplexitySupport  OBJECT-TYPE
        SYNTAX TruthValue 
        MAX-ACCESS read-write
        STATUS current
        DESCRIPTION
        "Enable/Disable the enforecement of minimum complexity of WPA-PSK."
	DEFVAL              { false }
        ::= { apSysConfig 17}
apSysConfWpaPskMinCharClass  OBJECT-TYPE
        SYNTAX  Integer32 (1..4)
        MAX-ACCESS read-write
        STATUS current
        DESCRIPTION
        "Indicates the minimum character class of WPA-PSK."
        ::= { apSysConfig 18}

apSysConfWpaPskMinLength  OBJECT-TYPE
        SYNTAX  Integer32 (8..16)
        MAX-ACCESS read-write
        STATUS current
        DESCRIPTION
        "Indicates the minimum length of WPA-PSK."
        ::= { apSysConfig 20}

apSysConfWpaPskMaxLength  OBJECT-TYPE
        SYNTAX  Integer32 (32..63)
        MAX-ACCESS read-write
        STATUS current
        DESCRIPTION
        "Indicates the maximum length of WPA-PSK."
        ::= { apSysConfig 21}

apSysConfWpaPskDiffFrmCurr  OBJECT-TYPE
        SYNTAX  TruthValue
        MAX-ACCESS read-write
        STATUS current
        DESCRIPTION
        "Enable/Disable to allow/prevent repetition of same WPA-PSK as new WPA-PSK. "
	DEFVAL              { false }
        ::= { apSysConfig 22}

apSysConfMD5Checksum   OBJECT-TYPE
        SYNTAX DisplayString
        MAX-ACCESS read-only
        STATUS current
        DESCRIPTION
                "Firmware MD5checksum for the AP."
        ::= { apSysConfig 23 }

apSysConfUsername       OBJECT-TYPE
        SYNTAX          DisplayString(SIZE(1..32))
        MAX-ACCESS      read-write
        STATUS          current
        DESCRIPTION
                "The name of the administrative user already configured in the system.
                The name can be up to 32 alphanumeric characters (including '-' and '_').
                The default name of the administrative user is 'cisco'."
        ::= { apSysConfig 24 }

apSysConfUserAccountsMax     OBJECT-TYPE
        SYNTAX      Integer32
        MAX-ACCESS  read-only
        STATUS      current
        DESCRIPTION
                "The maximum number of guest user accounts in the system."
        ::= { apSysConfig 25 }

apSysConfUserAccountsConfigured OBJECT-TYPE
        SYNTAX      Integer32
        MAX-ACCESS  read-only
        STATUS      current
        DESCRIPTION
                "The number of guest user accounts currently configured in the system."
        ::= { apSysConfig 26 }

-- apSysConfUserAccountTable

apSysConfUserAccountTable   OBJECT-TYPE
        SYNTAX      SEQUENCE OF ApSysConfUserAccountEntry
        MAX-ACCESS  not-accessible
        STATUS      current
        DESCRIPTION
                "A table of configurable user accounts."
        ::= { apSysConfig 27 }

apSysConfUserAccountEntry   OBJECT-TYPE
        SYNTAX      ApSysConfUserAccountEntry
        MAX-ACCESS  not-accessible
        STATUS      current
        DESCRIPTION
                "A configurable user account entry."
        INDEX   { apUserIndex }
        ::= { apSysConfUserAccountTable 1 }

ApSysConfUserAccountEntry ::= 
    SEQUENCE {
        apUserIndex             Integer32,
        apUserRowStatus         RowStatus,
        apUserName              DisplayString,
        apUserPassword          DisplayString,
        apUserType              INTEGER
        }

apUserIndex     OBJECT-TYPE
        SYNTAX      Integer32(1..4)
        MAX-ACCESS  not-accessible
        STATUS      current
        DESCRIPTION
                "The user account entry index."
         ::= { apSysConfUserAccountEntry 1 }

apUserRowStatus OBJECT-TYPE
        SYNTAX      RowStatus
        MAX-ACCESS  read-create
        STATUS      current
        DESCRIPTION
                "Status of an entry. Supported values are:

                active(1)      - Indicates user account is active.
                createAndGo(4) - Set to this value to create a user account.
                destroy(6)     - Set to this value to delete a user account.

                The administrator can only specify createAndGo and destroy.
                Object apUserIndex must be specified to create a table entry.
                After an entry is created its status is moved to active."
         ::= { apSysConfUserAccountEntry 2 }

apUserName      OBJECT-TYPE
        SYNTAX      DisplayString(SIZE(0..32))
        MAX-ACCESS  read-create
        STATUS      current
        DESCRIPTION
                "The user account entry name.
                The name can be up to 32 alphanumeric characters (including '-' and '_')."
        ::= { apSysConfUserAccountEntry 3 }

apUserPassword  OBJECT-TYPE
        SYNTAX      DisplayString(SIZE(0..80))
        MAX-ACCESS  read-create
        STATUS      current
        DESCRIPTION
                "The password associated with the user account.
                 Password contains characters from at least 3
                 of the following 4 categories: Uppercase letters, Lowercase letters,
                 Numbers, and Special characters available on a standard keyboard.
                 The range of the password length should be compliant with the 
                 configured minimum-password-length and maximum-password-length. 
                 alphanumeric characters. Special characters or spaces are not allowed.
                 This object returns string '*****' if password is configured."
        ::= { apSysConfUserAccountEntry 4 }

apUserType      OBJECT-TYPE
        SYNTAX      INTEGER {
                    admin(1),
                    guest(2)
                    }
        MAX-ACCESS  read-only
        STATUS      current
        DESCRIPTION
                "The user account entry type."
        DEFVAL { guest }
        ::= { apSysConfUserAccountEntry 5 }
-- end apSysConfUserAccountTable

-- *****************************************************************
-- i802System
-- *****************************************************************

i802SystemReboot OBJECT-TYPE
        SYNTAX          INTEGER { reboot (1) }
        MAX-ACCESS      read-write
        STATUS          current
        DESCRIPTION
                "Setting this object will cause the device to reboot. 
                The actual value is ignored."
        ::= { i802System 1 }

-- Keeping this object, just in case devicescape provide a fix.
--i802SystemUpgrade OBJECT-TYPE
--        SYNTAX          OCTET STRING (SIZE(0..100))
--        MAX-ACCESS      read-write
--        STATUS          current
--        DESCRIPTION
--        "Setting this object to a name of a file, causes the device to
--        download <upgrade URL>/<file>. After the file is downloaded,
--        it is installed replacing the existing firmware,
--        and the device is restarted."
--        ::= { i802System 2 }

i802SystemPersistConfig OBJECT-TYPE
        SYNTAX          INTEGER { persist (1) }
        MAX-ACCESS      read-write
        STATUS          current
        DESCRIPTION
        "Setting this object will cause the running config to be saved
        to the start-up config. The actual value is ignored."
        ::= { i802System 2 }

i802SystemFactoryReset OBJECT-TYPE
        SYNTAX          INTEGER {
                        reset (1)
                         }
        MAX-ACCESS      read-write
        STATUS          current
        DESCRIPTION
           "Setting this object to 'reset' will reset present 
           configuration to factory defaults. System will reboot after 
           setting configuration to its default.The actual value is ignored."
        ::= { i802System 3 }


i802SystemActivateBackupImage OBJECT-TYPE
        SYNTAX          INTEGER {
                        switch (1)
                         }
        MAX-ACCESS      read-write
        STATUS          current
        DESCRIPTION
           "Setting this object to activate backup image if the 
            platform supports dual image and the backup image is 
            a valid image. System will reboot to activate the
           backup image. The actual value is ignored."
        ::= { i802System 4 }

--*****************************************************************
--  apConfigSupplicant  OBJECT IDENTIFIER ::= { apGlobalConfig 5 }
--*****************************************************************

apSupplicantConfigStatus OBJECT-TYPE
    SYNTAX  INTEGER {
                up(1),
                down(2)
            }    
    MAX-ACCESS  read-write
    STATUS  current
    DESCRIPTION
            "Indicates whether 802.1x supplicant is enabled on this AP."
    DEFVAL { down }
    ::= { apConfigSupplicant 1 }

apSupplicantConfigUser OBJECT-TYPE
    SYNTAX  DisplayString (SIZE (1..64))
    MAX-ACCESS  read-write
    STATUS  current
    DESCRIPTION
        "Indicates the user name/identity used for 802.1x supplicant
        authentication.  ASCII printable characters are allowed,
        which includes upper and lower case alphabetic letters,
        numeric digits, and special symbols such as @ and #."
    ::= { apConfigSupplicant 2 }

apSupplicantConfigPassword OBJECT-TYPE
    SYNTAX  DisplayString( SIZE (1..64) )
    MAX-ACCESS  read-write
    STATUS  current
    DESCRIPTION
        "Configure the password used for 802.1X supplicant
        authentication.  If apSupplicantConfigEapMethod is set
        to md5 or peap, this value is the user's password.  If
        apSupplicantConfigEapMethod is set to tls, this value is the
        private key password.  ASCII printable characters are allowed,
        which includes upper and lower case alphabetic letters,
        numeric digits, and special symbols such as @ and #.
        The read of this parameter will return null string."
    ::= { apConfigSupplicant 3 }

apSupplicantConfigEapMethod OBJECT-TYPE
    SYNTAX  INTEGER {
                md5(1),
                peap(2),
                tls(3)
            }
    MAX-ACCESS  read-write
    STATUS  current
    DESCRIPTION
        "Configure the EAP Method used for 802.1X supplicant
        authentication."
    DEFVAL { md5 }
    ::= { apConfigSupplicant 4 }

apSupplicantCertificateFilePresent OBJECT-TYPE
    SYNTAX  INTEGER {
                yes(1),
                no(2)
            }
    MAX-ACCESS  read-only
    STATUS  current
    DESCRIPTION
        "Inidicates whether the TLS certificate file is present
        for use with 802.1X supplicant authentication."
    ::= { apConfigSupplicant 5 }

apSupplicantCertificateFileExpirationDate OBJECT-TYPE
    SYNTAX  DisplayString
    MAX-ACCESS  read-only
    STATUS  current
    DESCRIPTION
        "The expiration date of the TLS certificate"
    ::= { apConfigSupplicant 6 }

apSupplicantCertificateTFTPServerAddressType OBJECT-TYPE
    SYNTAX  InetAddressType
    MAX-ACCESS  read-only
    STATUS  current
    DESCRIPTION
            "Type of the IP address as defined in the InetAddress MIB.
             This is the address type of the TFTP server."
    REFERENCE "RFC 3291"
    DEFVAL { unknown }
    ::= { apSupplicantCertificateUpload 1 }

apSupplicantCertificateTFTPServerAddress OBJECT-TYPE
    SYNTAX  InetAddress
    MAX-ACCESS  read-write
    STATUS  current
    DESCRIPTION
            "The address of the TFTP Server from which to get the
             certificate file."
    ::= { apSupplicantCertificateUpload 2 }

apSupplicantCertificateTFTPServerPort OBJECT-TYPE
    SYNTAX  Integer32(1..65535)
    MAX-ACCESS  read-write
    STATUS  current
    DESCRIPTION
            "The port on the TFTP Server from which to get the
             certificate file."
    DEFVAL { 69 }
    ::= { apSupplicantCertificateUpload 3 }

apSupplicantCertificateUploadDirectory OBJECT-TYPE
    SYNTAX  DisplayString (SIZE (0..255))
    MAX-ACCESS  read-write
    STATUS  current
    DESCRIPTION
            "Directory on the server from which to get the certificate
             file.  This directory name does not contain the filename."
    ::= { apSupplicantCertificateUpload 4 }

apSupplicantCertificateUploadFilename OBJECT-TYPE
    SYNTAX  DisplayString (SIZE (0..64))
    MAX-ACCESS  read-write
    STATUS  current
    DESCRIPTION
            "File name on the server of the certificate file."
    ::= { apSupplicantCertificateUpload 5 }

apSupplicantCertificateUploadProtocol OBJECT-TYPE
    SYNTAX INTEGER {
        tftp(1)
    }
    MAX-ACCESS  read-only
    STATUS  current
    DESCRIPTION
            "The protocol used for uploading the certificate file."
    DEFVAL { tftp }
    ::= { apSupplicantCertificateUpload 6 }

apSupplicantCertificateUploadStart OBJECT-TYPE
    SYNTAX INTEGER {
        enable(1),
        disable(2)
    }
    MAX-ACCESS  read-write
    STATUS  current
    DESCRIPTION
            "This object initiates the certificate file upload to the AP."
    DEFVAL { disable }
    ::= { apSupplicantCertificateUpload 7 }

apSupplicantCertificateUploadStatus OBJECT-TYPE
    SYNTAX INTEGER {
        notStarted(1),
        inProgress(2),
        success(3),
        failed(4)
    }
    MAX-ACCESS  read-only
    STATUS  current
    DESCRIPTION
            "The upload status of the certificate file to the AP."
    DEFVAL { transferNotInitiated }
    ::= { apSupplicantCertificateUpload 8 }


--****************************************************************
--   apHost          OBJECT IDENTIFIER ::= { apGlobalConfig 5 }
--****************************************************************

        apHostId            OBJECT-TYPE
            SYNTAX          DisplayString(SIZE(1..63))
            MAX-ACCESS      read-write
            STATUS          current
            DESCRIPTION
           "Hostname of this system. This can be concatenated with
           apHostDomain to form the Fully Qualified Domain Name (FQDN)
                     for this AP."
        ::= { apHost 1 }

        apHostDns1Type      OBJECT-TYPE
                            SYNTAX InetAddressType
                            MAX-ACCESS read-only
                            STATUS current
           DESCRIPTION
       "The address type for the first entry in the DNS server list.
       Value of address type depends on first DNS server address."
        ::= { apHost 2 }

        apHostDns1Addr      OBJECT-TYPE
                            SYNTAX InetAddress
                            MAX-ACCESS read-only
                            STATUS current
                            DESCRIPTION
        "Address of the first entry in the active DNS server list."
        ::= { apHost 3 }

        apHostDns2Type      OBJECT-TYPE
                            SYNTAX InetAddressType
                            MAX-ACCESS read-only
                            STATUS current
                            DESCRIPTION
        "Address type for the second entry in the DNS Server List.
         Value of address type depends on second DNS server address
                            DNS name."
        ::= { apHost 4 }

        apHostDns2Addr   OBJECT-TYPE
                            SYNTAX InetAddress
                            MAX-ACCESS read-only
                            STATUS current
                            DESCRIPTION
        "Address of the second entry in the active DNS server list."
        ::= { apHost 5 }


apHostDomain     OBJECT-TYPE
                            SYNTAX DisplayString
                            MAX-ACCESS read-only
                            STATUS current
                            DESCRIPTION
        "Domain name for this host. Can be appended to apHostId to 
        form the Fully Qualified Domain Name (FQDN) for this system."
        ::= { apHost 6 }

        apHostStatDns1Type  OBJECT-TYPE
                            SYNTAX InetAddressType
                            MAX-ACCESS read-only
                            STATUS current
                            DESCRIPTION
                            "The type of apHostStatDns1Addr."
         DEFVAL { unknown }
        ::= { apHost 7 }

        apHostStatDns1Addr  OBJECT-TYPE
                            SYNTAX InetAddress
                            MAX-ACCESS read-write
                            STATUS current
                            DESCRIPTION
        "Address that will be used as the first entry in the DNS
        server list if apHostDnsViaDhcp is false or no DNS server
        list is supplied by DHCP."
        ::= { apHost 8 }

        apHostStatDns2Type  OBJECT-TYPE
                            SYNTAX InetAddressType
                            MAX-ACCESS read-only
                            STATUS current
                            DESCRIPTION
                           "The type of apHostStatDns2Addr."
    DEFVAL { unknown }
        ::= { apHost 9 }

        apHostStatDns2Addr  OBJECT-TYPE
                            SYNTAX InetAddress
                            MAX-ACCESS read-write
                            STATUS current
                            DESCRIPTION
        "Address that will be used as the second entry in the DNS 
        server list if apHostDnsViaDhcp is false or no DNS server
        list is supplied by DHCP."
        ::= { apHost 10 }


apHostStatDomain OBJECT-TYPE
                            SYNTAX DisplayString(SIZE(1..64))
                            MAX-ACCESS read-write
                            STATUS current
                            DESCRIPTION
        "Domain name to be used if apHostDnsViaDhcp is false or a
                            domain name is not supplied by DHCP."
        ::= { apHost 11 }
 
apHostDnsViaDhcp OBJECT-TYPE
                            SYNTAX TruthValue
                            MAX-ACCESS read-write
                            STATUS current
       DESCRIPTION
       "Indicates whether or not this host will try to obtain DNS 
	server information from a DHCP server."
        DEFVAL              { true }                    
        ::= { apHost 12 }


--#IFDEF IPV6_MGMT       DNS IPv6 Support

apHostDnsipv61Type      OBJECT-TYPE
                            SYNTAX InetAddressType
                            MAX-ACCESS read-only
                            STATUS current
           DESCRIPTION
       "The address type for the first entry in the DNS server list.
       Value of address type depends on first DNSv6 server address."
        ::= { apHost 13 }

apHostDnsipv61Addr      OBJECT-TYPE
                            SYNTAX InetAddress
                            MAX-ACCESS read-only
                            STATUS current
                            DESCRIPTION
        "Address of the first entry in the active DNSv6 server list."
        ::= { apHost 14 }

apHostDnsipv62Type      OBJECT-TYPE
                            SYNTAX InetAddressType
                            MAX-ACCESS read-only
                            STATUS current
                            DESCRIPTION
        "Address type for the second entry in the DNS Server List.
         Value of address type depends on second DNSv6 server address
                            DNS name."
        ::= { apHost 15 }

apHostDnsipv62Addr   OBJECT-TYPE
                            SYNTAX InetAddress
                            MAX-ACCESS read-only
                            STATUS current
                            DESCRIPTION
        "Address of the second entry in the active DNSv6 server list."
        ::= { apHost 16 }

apHostStatDnsipv61Type  OBJECT-TYPE
                            SYNTAX InetAddressType
                            MAX-ACCESS read-only
                            STATUS current
                            DESCRIPTION
                            "The type of apHostStatDnsipv61Addr."
         DEFVAL { unknown }
        ::= { apHost 17 }

apHostStatDnsipv61Addr  OBJECT-TYPE
                            SYNTAX InetAddress
                            MAX-ACCESS read-write
                            STATUS current
                            DESCRIPTION
        "Address that will be used as the first entry in the DNS
        server list if apHostDnsViaDhcpv6 is false or no DNS server
        list is supplied by DHCP."
        ::= { apHost 18 }

apHostStatDnsipv62Type  OBJECT-TYPE
                            SYNTAX InetAddressType
                            MAX-ACCESS read-only
                            STATUS current
                            DESCRIPTION
                           "The type of apHostStatDnsipv62Addr."
    DEFVAL { unknown }
        ::= { apHost 19 }

apHostStatDnsipv62Addr  OBJECT-TYPE
                            SYNTAX InetAddress
                            MAX-ACCESS read-write
                            STATUS current
                            DESCRIPTION
        "Address that will be used as the second entry in the DNS 
        server list if apHostDnsViaDhcpv6 is false or no DNS server
        list is supplied by DHCP."
        ::= { apHost 20 }

apHostDnsViaDhcpv6 OBJECT-TYPE
                            SYNTAX TruthValue
                            MAX-ACCESS read-write
                            STATUS current
       DESCRIPTION
       "Indicates whether or not this host will try to obtain DNS 
	server information from a DHCPv6 server."
        DEFVAL              { true }                    
        ::= { apHost 21 }

--#ENDIF  DNS IPv6 Support ends


--*****************************************************************
--      apMgmtAccess          OBJECT IDENTIFIER ::= { apGlobalConfig 7 }
--*****************************************************************

        apMgmtAccTelnet     	OBJECT-TYPE
    SYNTAX       INTEGER {
	         up (1),
	         down (2)
	         }
    MAX-ACCESS   read-write
    STATUS       current
    DESCRIPTION
        "Indicates whether management access is allowed
         through the Telnet interface."
        DEFVAL          { up }                        
        ::= { apMgmtAccess 1 }   

        apMgmtAccHttpsStatus   	OBJECT-TYPE
    SYNTAX       INTEGER {
                 up (1),
                 down (2)
                 }
    MAX-ACCESS   read-write
    STATUS       current
    DESCRIPTION
        "Indicates whether management access is allowed
         through the HTTPS interface."
        DEFVAL          { up }                        
        ::= { apMgmtAccess 2 }  

        apMgmtAccHttpStatus    	OBJECT-TYPE
    SYNTAX       INTEGER {
    	         up (1),
    	         down (2)
                 }
    MAX-ACCESS   read-write
    STATUS       current
    DESCRIPTION
        "Indicates whether management access is allowed
         through the HTTP interface."
        DEFVAL          { up }                        
        ::= { apMgmtAccess 3 }   

        apMgmtAccHttpPort    	OBJECT-TYPE
    SYNTAX       Integer32(1025..65535) 
    MAX-ACCESS   read-write
    STATUS       current
    DESCRIPTION
        "Indicates the port on which the web server will be enabled."
        DEFVAL          { 80 }                                
        ::= { apMgmtAccess 4 }   

        apMgmtAccSerial     	OBJECT-TYPE
    SYNTAX       INTEGER {
    	         up (1),
    	         down (2)
                 }
    MAX-ACCESS   read-write
    STATUS       current
    DESCRIPTION
        "Indicates whether management access is allowed
         through the Serial interface."
        DEFVAL          { up }
        ::= { apMgmtAccess 5 }   

        apMgmtAccNtp        	OBJECT-TYPE
    SYNTAX       INTEGER {
    	         up (1),
    	         down (2)
                 }
    MAX-ACCESS   read-write
    STATUS       current
    DESCRIPTION
        "Indicates whether the Network Time Protocol(NTP) server
         will be enabled."
        DEFVAL          { up }                                
        ::= { apMgmtAccess 6 }   

    apMgmtAccNtpAddrType	OBJECT-TYPE
    SYNTAX       InetAddressType
    MAX-ACCESS   read-write
    STATUS       current
    DESCRIPTION
        "Indicates the type of address being used for the
         NTP server. IP addresses or hostname.
         The inet address type must be configured before
         configuring IP address or domain name"

    DEFVAL { unknown }
        ::= { apMgmtAccess 7 }
            
    apMgmtAccNtpAddr    	OBJECT-TYPE
    SYNTAX       InetAddress
    MAX-ACCESS   read-write
    STATUS       current
    DESCRIPTION
        "Indicates the address(DNS/IP address) of the NTP server.
         The inet address type must be configured before
         configuring IP address or domain name"

        ::= { apMgmtAccess 8 }
           
          
        apMgmtAccACLMode    	OBJECT-TYPE
    SYNTAX       INTEGER {
    	         up (1),
    	         down (2)
                 }
    MAX-ACCESS   read-write
    STATUS       current
    DESCRIPTION
        "Indicates whether management ACL for WEB sessions, CLI and SNMP 
                                is enabled or disabled."
        DEFVAL          { down }                        
        ::= { apMgmtAccess 9 }

        apMgmtAccACLIpAddr1Type OBJECT-TYPE
                                SYNTAX InetAddressType
                                MAX-ACCESS read-only
                                STATUS current
          DESCRIPTION
          "The Internet address type of apMgmtAccACLIpAddr1."
        ::= { apMgmtAccess 10 }
           
        apMgmtAccACLIpAddr1    	OBJECT-TYPE
    SYNTAX       InetAddress
    MAX-ACCESS   read-write
    STATUS       current
    DESCRIPTION
        "Indicates the IPv4 address of the host that can have
        web, cli and snmp access to the AP."
        ::= { apMgmtAccess 11 }
           
        apMgmtAccACLIpAddr2Type OBJECT-TYPE
                                SYNTAX InetAddressType
                                MAX-ACCESS read-only
                                STATUS current
          DESCRIPTION
          "The Internet address type of apMgmtAccACLIpAddr2."
        ::= { apMgmtAccess 12 }
           
        apMgmtAccACLIpAddr2    	OBJECT-TYPE
    SYNTAX       InetAddress
    MAX-ACCESS   read-write
    STATUS       current
    DESCRIPTION
        "Indicates the IPv4 address of the host that can have
         web, cli and snmp access to the AP."
        ::= { apMgmtAccess 13 }
           
        apMgmtAccACLIpAddr3Type OBJECT-TYPE
                                SYNTAX InetAddressType
                                MAX-ACCESS read-only
                                STATUS current
          DESCRIPTION
          "The Internet address type of apMgmtAccACLIpAddr3."
        ::= { apMgmtAccess 14 }
           
        apMgmtAccACLIpAddr3    	OBJECT-TYPE
    SYNTAX       InetAddress
    MAX-ACCESS   read-write
    STATUS       current
    DESCRIPTION
        "Indicates the IPv4 address of the host that can have
         web, cli and snmp access to the AP."
        ::= { apMgmtAccess 15 }
           
        apMgmtAccACLIpAddr4Type OBJECT-TYPE
                                SYNTAX InetAddressType
                                MAX-ACCESS read-only
                                STATUS current
          DESCRIPTION
          "The Internet address type of apMgmtAccACLIpAddr4."
        ::= { apMgmtAccess 16 }
           
        apMgmtAccACLIpAddr4    	OBJECT-TYPE
    SYNTAX       InetAddress
    MAX-ACCESS   read-write
    STATUS       current
    DESCRIPTION
        "Indicates the IPv4 address of the host that can have
         web, cli and snmp access to the AP."
        ::= { apMgmtAccess 17 }
           
        apMgmtAccACLIpAddr5Type OBJECT-TYPE
                                SYNTAX InetAddressType
                                MAX-ACCESS read-only
                                STATUS current
          DESCRIPTION
          "The Internet address type of apMgmtAccACLIpAddr5."
        ::= { apMgmtAccess 18 }
           
        apMgmtAccACLIpAddr5    	OBJECT-TYPE
    SYNTAX       InetAddress
    MAX-ACCESS   read-write
    STATUS       current
    DESCRIPTION
        "Indicates the IPv4 address of the host that can have
         web, cli and snmp access to the AP."
        ::= { apMgmtAccess 19 }

        apMgmtAccACLIpv6Addr1Type OBJECT-TYPE
                                SYNTAX InetAddressType
                                MAX-ACCESS read-only
                                STATUS current
                                DESCRIPTION
                                "The Internet address type of apMgmtAccACLIpv6Addr1."
        ::= { apMgmtAccess 20 }

        apMgmtAccACLIpv6Addr1   OBJECT-TYPE
                                SYNTAX InetAddress
                                MAX-ACCESS read-write
                                STATUS current
          DESCRIPTION
          "Indicates the IPv6 address of the host that can have
                                web, cli and snmp access to the AP."
        ::= { apMgmtAccess 21 }

        apMgmtAccACLIpv6Addr2Type OBJECT-TYPE
                                SYNTAX InetAddressType
                                MAX-ACCESS read-only
                                STATUS current
          DESCRIPTION
          "The Internet address type of apMgmtAccACLIpv6Addr2."
        ::= { apMgmtAccess 22 }

        apMgmtAccACLIpv6Addr2   OBJECT-TYPE
                                SYNTAX InetAddress
                                MAX-ACCESS read-write
                                STATUS current
          DESCRIPTION
          "Indicates the IPv6 address of the host that can have
           web, cli and snmp access to the AP."
        ::= { apMgmtAccess 23 }

        apMgmtAccACLIpv6Addr3Type OBJECT-TYPE
                                SYNTAX InetAddressType
                                MAX-ACCESS read-only
                                STATUS current
          DESCRIPTION
          "The Internet address type of apMgmtAccACLIpv6Addr3."
        ::= { apMgmtAccess 24 }

        apMgmtAccACLIpv6Addr3   OBJECT-TYPE
                                SYNTAX InetAddress
                                MAX-ACCESS read-write
                                STATUS current
          DESCRIPTION
          "Indicates the IPv6 address of the host that can have
           web, cli and snmp access to the AP."
        ::= { apMgmtAccess 25 }

        apMgmtAccACLIpv6Addr4Type OBJECT-TYPE
                                SYNTAX InetAddressType
                                MAX-ACCESS read-only
                                STATUS current
          DESCRIPTION
          "The Internet address type of apMgmtAccACLIpv6Addr4."
        ::= { apMgmtAccess 26 }

        apMgmtAccACLIpv6Addr4   OBJECT-TYPE
                                SYNTAX InetAddress
                                MAX-ACCESS read-write
                                STATUS current
          DESCRIPTION
          "Indicates the IPv6 address of the host that can have
           web, cli and snmp access to the AP."
        ::= { apMgmtAccess 27 }

        apMgmtAccACLIpv6Addr5Type OBJECT-TYPE
                                SYNTAX InetAddressType
                                MAX-ACCESS read-only
                                STATUS current
          DESCRIPTION
          "The Internet address type of apMgmtAccACLIpv6Addr5."
        ::= { apMgmtAccess 28 }

        apMgmtAccACLIpv6Addr5   OBJECT-TYPE
                                SYNTAX InetAddress
                                MAX-ACCESS read-write
                                STATUS current
          DESCRIPTION
          "Indicates the IPv6 address of the host that can have
           web, cli and snmp access to the AP."
        ::= { apMgmtAccess 29 }

        apMgmtAccSerialSpeed	OBJECT-TYPE
    SYNTAX       INTEGER {
    	         baud9600 (1),
    	         baud19200 (2),
    	         baud38400 (3),
    	         baud57600 (4),
    	         baud115200 (5)
                 }
    MAX-ACCESS   read-write
    STATUS       current
    DESCRIPTION
        "Speed of the Serial Port."
        DEFVAL          { baud115200 }
        ::= { apMgmtAccess 30 }   

apMgmtAccSsh    OBJECT-TYPE
    SYNTAX      INTEGER {
    	         up (1),
    	         down (2)
                 }
    MAX-ACCESS   read-write
    STATUS       current
    DESCRIPTION
        "Indicates whether management access is allowed
         through the SSH interface."
        DEFVAL          { up }                        
        ::= { apMgmtAccess 31 }   

apMgmtAccGenSslCert   	OBJECT-TYPE
    SYNTAX       INTEGER{ generateCertificate (1) }
    MAX-ACCESS   read-write
    STATUS       current
    DESCRIPTION
        "Setting this object will cause the SSL certificate to
         be regenerated.  The https server will be cycled."
        ::= { apMgmtAccess 32 }  

        apMgmtAccSessionMax    	OBJECT-TYPE
                            	SYNTAX Integer32(1..10) 
                            	MAX-ACCESS read-write
                            	STATUS current
                            	DESCRIPTION
                            	"Indicates the maximum number of web sessions
                            	allowed at any one time ... the combined number 
                                of http and https sessions."
        DEFVAL          { 5 }                                
        ::= { apMgmtAccess 33 }   

        apMgmtAccSessionTimeout OBJECT-TYPE
                            	SYNTAX Integer32(1..60) 
                            	MAX-ACCESS read-write
                            	STATUS current
                            	DESCRIPTION
                            	"Indicates the web session timeout in minutes.
                            	This applies to both http and https sessions."
        DEFVAL          { 10 }                                
        ::= { apMgmtAccess 34 }   

        apMgmtAccBonjourStatus   	OBJECT-TYPE
    SYNTAX       INTEGER {
                 up (1),
                 down (2)
                 }
    MAX-ACCESS   read-write
    STATUS       current
    DESCRIPTION
        "Indicates whether Bonjour is enabled on the device."
        DEFVAL          { up }                        
        ::= { apMgmtAccess 35 }  

        apMgmtAccHttpsPort       OBJECT-TYPE
    SYNTAX       Integer32(1025..65535)
    MAX-ACCESS   read-write
    STATUS       current
    DESCRIPTION
        "Indicates the port on which the web server (https) will be enabled."
        DEFVAL          { 443 }
        ::= { apMgmtAccess 36 }


--******************************************************************
-- apMgmtConfig             OBJECT IDENTIFIER ::= { apGlobalConfig 8 }    
--******************************************************************

        apManagementVlanID	OBJECT-TYPE
    SYNTAX	 Integer32(0..4094)
    MAX-ACCESS   read-write
    STATUS       current
    DESCRIPTION
        "VLAN-ID of the management VLAN."
        DEFVAL          { 1 }                                
        ::= { apMgmtConfig 1 }

        apManagementInterface	OBJECT-TYPE
    SYNTAX	 DisplayString
    MAX-ACCESS   read-only
    STATUS       current
    DESCRIPTION
        "Interface for management communication."
        ::= { apMgmtConfig 2 }

        apManagementStaticipType OBJECT-TYPE
                                SYNTAX  InetAddressType
                                MAX-ACCESS read-only
                                STATUS current
          DESCRIPTION
          "The Internet address type of apManagementStaticip."
        ::= { apMgmtConfig 3 }

        apManagementStaticip   	OBJECT-TYPE
    SYNTAX	 InetAddress
    MAX-ACCESS   read-write
    STATUS       current
    DESCRIPTION
        "Static IP address of the management interface."
        ::= { apMgmtConfig 4 }

        apManagementStaticMaskType OBJECT-TYPE
                                SYNTAX  InetAddressType
                                MAX-ACCESS read-only
                                STATUS current
          DESCRIPTION
          "The Internet address type of apManagementStaticMask."
        ::= { apMgmtConfig 5 }

        apManagementStaticMask 	OBJECT-TYPE
    SYNTAX	 InetAddress
    MAX-ACCESS   read-write
    STATUS       current
    DESCRIPTION
        "Static mask of the management interface."
        ::= { apMgmtConfig 6 }

        apManagementIPType      OBJECT-TYPE
                                SYNTAX InetAddressType
                                MAX-ACCESS read-only
                                STATUS current
          DESCRIPTION
          "The Internet address type of apManagementIP."
        ::= { apMgmtConfig 7 }

        apManagementIP   	OBJECT-TYPE
    SYNTAX	 InetAddress(SIZE(0|4|16))
    MAX-ACCESS   read-only
    STATUS       current
    DESCRIPTION
        "IP address of the management interface."
        ::= { apMgmtConfig 8 }

        apManagementMaskType    OBJECT-TYPE
                                SYNTAX InetAddressType
                                MAX-ACCESS read-only
                                STATUS current
          DESCRIPTION
          "The Internet address type of apManagementMask."
        ::= { apMgmtConfig 9 }

        apManagementMask   	OBJECT-TYPE
    SYNTAX       InetAddress(SIZE(0|4|16))
    MAX-ACCESS   read-only
    STATUS       current
    DESCRIPTION
        "IP mask of the management interface."
        ::= { apMgmtConfig 10 }

        apManagementMAC  	OBJECT-TYPE
    SYNTAX	 MacAddress
    MAX-ACCESS   read-only
    STATUS       current
    DESCRIPTION
        "MAC address of the management interface."
        ::= { apMgmtConfig 11 }

        apManagementDhcpStatus 	OBJECT-TYPE
    SYNTAX	 INTEGER {
    	         up(1),
                                        down(2)
    	         }
    MAX-ACCESS   read-write
    STATUS       current
    DESCRIPTION
        "Indicates whether DHCP is enabled for management interface."
        DEFVAL                  { up }                        
        ::= { apMgmtConfig 12 }
        
        apUntaggedVlanID	        OBJECT-TYPE
    SYNTAX	 Integer32(1..4094)
    MAX-ACCESS   read-write
    STATUS       current
    DESCRIPTION
        "VLAN to which untagged traffic is assigned."
        DEFVAL          { 1 }                        
        ::= { apMgmtConfig 13 }

        apUntaggedVlanStatus    	OBJECT-TYPE
    SYNTAX	 INTEGER {
    	         up(1),
                                        down(2)
    	         }
    MAX-ACCESS   read-write
    STATUS       current
    DESCRIPTION
        "Untagged VLAN interface status."
        DEFVAL                  { up }                                
        ::= { apMgmtConfig 14 }

        apManagementIPv6Status  OBJECT-TYPE
                                SYNTAX  INTEGER {
                                        up(1),
                                        down(2)
                                        }
                                MAX-ACCESS read-write
                                STATUS current
          DESCRIPTION
          "Enable or disable IPv6 support on the management interface."
        DEFVAL                  { up }
        ::= { apMgmtConfig 15 }

        apManagementIPv6AutoConfigStatus        OBJECT-TYPE
                                SYNTAX  INTEGER {
                                        up(1),
                                        down(2)
                                        }
                                MAX-ACCESS read-write
                                STATUS current
          DESCRIPTION
          "Enable or disable IPv6 Auto address configuration 
           support on the management interface."
        DEFVAL                  { up }
        ::= { apMgmtConfig 16 }

        apManagementStaticIPv6Type OBJECT-TYPE
                                SYNTAX InetAddressType
                                MAX-ACCESS read-only
                                STATUS current
          DESCRIPTION
          "The Internet address type of apManagementStaticIPv6."
        ::= { apMgmtConfig 17 }

        apManagementStaticIPv6  OBJECT-TYPE
                                SYNTAX  InetAddress
                                MAX-ACCESS read-write
                                STATUS current
          DESCRIPTION
          "Static IPv6 address of the management interface."
        ::= { apMgmtConfig 18 }

        apManagementStaticIPv6PrefixLength      OBJECT-TYPE
                                SYNTAX  INTEGER (0..128)
                                MAX-ACCESS read-write
                                STATUS current
          DESCRIPTION
          "Static prefix length of the static ipv6 address of 
                                 management interface."
        ::= { apMgmtConfig 19 }
    
        apManagementAutoConfigLinkLocalType OBJECT-TYPE
                                SYNTAX InetAddressType
                                MAX-ACCESS read-only
                                STATUS current
                                DESCRIPTION
        "Internet address type of apManagementAutoConfigLinkLocal."
        ::= { apMgmtConfig 20 }

        apManagementAutoConfigLinkLocal OBJECT-TYPE
                                SYNTAX      InetAddress
                                MAX-ACCESS  read-only
                                STATUS      current
          DESCRIPTION
           "The Autoconfigured Link local IPv6 address of 
                                  management interface."
        ::= { apMgmtConfig 21 }

        apManagementAutoConfigIPv6GlobalType OBJECT-TYPE
                                SYNTAX InetAddressType
                                MAX-ACCESS read-only
                                STATUS current
                                DESCRIPTION
        "Internet address type of apManagementAutoConfigIPv6Global."
        ::= { apMgmtConfig 22 }

        apManagementAutoConfigIPv6Global OBJECT-TYPE
                                SYNTAX      InetAddress
                                MAX-ACCESS  read-only
                                STATUS      current
          DESCRIPTION
          "The Autoconfigured global IPv6 address of 
                                 management interface."
        ::= { apMgmtConfig 23 }

        apManagementStaticIPv6AddrStatus  OBJECT-TYPE
                                SYNTAX      DisplayString
                                MAX-ACCESS  read-only
                                STATUS      current
          DESCRIPTION
          "Indicates the operational status  of static IPv6 address
                                 assigend to management interface."
        ::= { apMgmtConfig 24 }

	    apManagementIPv6        OBJECT-TYPE
                                SYNTAX  InetAddress
                                MAX-ACCESS   read-only
                                STATUS       current
          DESCRIPTION
          "IPv6 address of the management interface."
        ::= { apMgmtConfig 25 }

        apManagementDhcpv6Status        OBJECT-TYPE
                                SYNTAX      TruthValue
                                MAX-ACCESS   read-write
                                STATUS       current
          DESCRIPTION
          "Indicates whether DHCPv6 is enabled for management interface."
        DEFVAL                  { true }
        ::= { apMgmtConfig 26 }


--*****************************************************************
--      apGlobalRadiusServer
--*****************************************************************

 apGlobalRadiusAccMode	        OBJECT-TYPE
               SYNTAX	        INTEGER{
                                        up(1),
                                        down(2)
                                }
               MAX-ACCESS       read-write
               STATUS           current
    DESCRIPTION      
        "Indicates if RADIUS Accounting has been enabled or not."
        DEFVAL          { down }        
        ::= { apGlobalRadiusServer 1 }
        
apGlobalRadiusIPAddressType   	OBJECT-TYPE
            SYNTAX	            InetAddressType
            MAX-ACCESS          read-write
            STATUS              current
    DESCRIPTION         
        "Indicates the IP address type of the global 
                                RADIUS server on your network."
        DEFVAL          { ipv4 }                                
        ::= { apGlobalRadiusServer 2}

apGlobalRadiusPrimaryServerIPAddress         OBJECT-TYPE
            SYNTAX              InetAddress
            MAX-ACCESS          read-write
            STATUS              current
    DESCRIPTION         
        "Indicates the IP address of the Primary RADIUS server
         on user network that all VAPs use by default."
        ::= { apGlobalRadiusServer 3 }

apGlobalRadiusBackuponeServerIPAddressType OBJECT-TYPE
            SYNTAX              InetAddressType
            MAX-ACCESS          read-only
            STATUS              current
    DESCRIPTION         
        "The Internet address type of
         apGlobalRadiusBackuponeServerIPAddress."
        ::= { apGlobalRadiusServer 4 }

apGlobalRadiusBackuponeServerIPAddress         OBJECT-TYPE
            SYNTAX              InetAddress
            MAX-ACCESS          read-write
            STATUS              current
    DESCRIPTION         
        "Indicates the IP address of the first backup RADIUS server
         on user network that all VAPs use by default."
        ::= { apGlobalRadiusServer 5 }

apGlobalRadiusBackuptwoServerIPAddressType OBJECT-TYPE
            SYNTAX              InetAddressType
            MAX-ACCESS          read-only
            STATUS              current
    DESCRIPTION         
        "The Internet address type of
         apGlobalRadiusBackuptwoServerIPAddress."
        ::= { apGlobalRadiusServer 6 }

apGlobalRadiusBackuptwoServerIPAddress         OBJECT-TYPE
            SYNTAX              InetAddress
            MAX-ACCESS          read-write
            STATUS              current
    DESCRIPTION         
        "Indicates the IP address of the second backup RADIUS server
         on user network that all VAPs use by default."
        ::= { apGlobalRadiusServer 7 }

apGlobalRadiusBackupthreeServerIPAddressType OBJECT-TYPE
            SYNTAX              InetAddressType
            MAX-ACCESS          read-only
            STATUS              current
    DESCRIPTION         
        "The Internet address type of
         apGlobalRadiusBackupthreeServerIPAddress."
        ::= { apGlobalRadiusServer 8 }

apGlobalRadiusBackupthreeServerIPAddress         OBJECT-TYPE
            SYNTAX              InetAddress
            MAX-ACCESS          read-write
            STATUS              current
    DESCRIPTION         
        "Indicates the IP address of the third backup RADIUS server
         on user network that all VAPs use by default."
        ::= { apGlobalRadiusServer 9 }

apGlobalRadiusPrimaryServerIPv6AddressType OBJECT-TYPE
            SYNTAX              InetAddressType
            MAX-ACCESS          read-only
            STATUS              current
    DESCRIPTION         
        "The Internet address type of
         apGlobalRadiusPrimaryServerIPv6Address."
        ::= { apGlobalRadiusServer 10 }

apGlobalRadiusPrimaryServerIPv6Address      OBJECT-TYPE
            SYNTAX              InetAddress
            MAX-ACCESS          read-write
            STATUS              current
    DESCRIPTION         
        "Indicates the IPv6 address of the Primary RADIUS server
         on user network that all VAPs use."
        ::= { apGlobalRadiusServer 11 }

apGlobalRadiusBackuponeServerIPv6AddressType OBJECT-TYPE
            SYNTAX              InetAddressType
            MAX-ACCESS          read-only
            STATUS              current
    DESCRIPTION         
        "The Internet address type of
         apGlobalRadiusBackuponeServerIPv6Address."
        ::= { apGlobalRadiusServer 12 }

apGlobalRadiusBackuponeServerIPv6Address      OBJECT-TYPE
            SYNTAX              InetAddress
            MAX-ACCESS          read-write
            STATUS              current
    DESCRIPTION         
        "Indicates the IPv6 address of the first backup RADIUS server
         on user network that all VAPs use."
        ::= { apGlobalRadiusServer 13 }

apGlobalRadiusBackuptwoServerIPv6AddressType OBJECT-TYPE
            SYNTAX              InetAddressType
            MAX-ACCESS          read-only
            STATUS              current
    DESCRIPTION         
        "The Internet address type of
         apGlobalRadiusBackuptwoServerIPv6Address."
        ::= { apGlobalRadiusServer 14 }

apGlobalRadiusBackuptwoServerIPv6Address      OBJECT-TYPE
            SYNTAX              InetAddress
            MAX-ACCESS          read-write
            STATUS              current
    DESCRIPTION         
        "Indicates the IPv6 address of the second backup RADIUS server
         on user network that all VAPs use."
        ::= { apGlobalRadiusServer 15 }

apGlobalRadiusBackupthreeServerIPv6AddressType OBJECT-TYPE
            SYNTAX              InetAddressType
            MAX-ACCESS          read-only
            STATUS              current
    DESCRIPTION         
        "Internet address type of
         apGlobalRadiusBackupthreeServerIPv6Address."
        ::= { apGlobalRadiusServer 16 }

apGlobalRadiusBackupthreeServerIPv6Address      OBJECT-TYPE
            SYNTAX              InetAddress
            MAX-ACCESS          read-write
            STATUS              current
    DESCRIPTION         
        "Indicates the IPv6 address of the third backup RADIUS 
         server on user network that all VAPs use."
        ::= { apGlobalRadiusServer 17 }

apGlobalRadiusPrimaryServerKey   OBJECT-TYPE
               SYNTAX	        DisplayString(SIZE(1..64))
               MAX-ACCESS       read-write
               STATUS           current
               DESCRIPTION
        "Indicates the shared secret key for the global primary
         RADIUS server. The text you enter will be displayed as '*'
         characters to prevent others from seeing the RADIUS key as
         you type. Default value of global RADIUS key is 'secret'."
        ::= { apGlobalRadiusServer 18 }

apGlobalRadiusBackuponeServerKey          OBJECT-TYPE
               SYNTAX           DisplayString(SIZE(1..64))
               MAX-ACCESS       read-write
               STATUS           current
               DESCRIPTION
        "Indicates the shared secret key for the global first backup
        RADIUS server. The text you enter will be displayed as '*'
        characters to prevent others from seeing the RADIUS key as
        you type. Default value of global RADIUS key is empty string."
        ::= { apGlobalRadiusServer 19 }

apGlobalRadiusBackuptwoServerKey          OBJECT-TYPE
               SYNTAX           DisplayString(SIZE(1..64))
               MAX-ACCESS       read-write
               STATUS           current
               DESCRIPTION
        "Indicates the shared secret key for the global second backup
        RADIUS server. The text you enter will be displayed as '*'
        characters to prevent others from seeing the RADIUS key as
        you type. Default value of global RADIUS key is empty string."
        ::= { apGlobalRadiusServer 20 }

apGlobalRadiusBackupthreeServerKey          OBJECT-TYPE
               SYNTAX           DisplayString(SIZE(1..64))
               MAX-ACCESS       read-write
               STATUS           current
               DESCRIPTION
        "Indicates the shared secret key for the global third backup
        RADIUS server. The text you enter will be displayed as '*'
        characters to prevent others from seeing the RADIUS key as
        you type. Default value of global RADIUS key is empty string."
        ::= { apGlobalRadiusServer 21 }
        

--*****************************************************************
--  apStaticIpRoute         OBJECT IDENTIFIER ::= { apGlobalConfig 9 }
--*****************************************************************

 apStaticIpRouteDestType   OBJECT-TYPE
    SYNTAX      InetAddressType
    MAX-ACCESS  read-only
    STATUS      current
    DESCRIPTION
            "The Internet address type of apStaticIpRouteDest."
    ::= { apStaticIpRoute 1 }
    
 apStaticIpRouteDest   OBJECT-TYPE
    SYNTAX      InetAddress
    MAX-ACCESS  read-write
    STATUS      current
    DESCRIPTION
            "Destination IP of the static route."
    ::= { apStaticIpRoute 2 }

 apStaticIpRouteMaskType   OBJECT-TYPE
    SYNTAX      InetAddressType
    MAX-ACCESS  read-only
    STATUS      current
    DESCRIPTION
            "The Internet address type of apStaticIpRouteMask."
    ::= { apStaticIpRoute 3 }
    
 apStaticIpRouteMask   OBJECT-TYPE
    SYNTAX      InetAddress
    MAX-ACCESS  read-write
    STATUS      current
    DESCRIPTION
            "Network Mask of the static route."
    ::= { apStaticIpRoute 4 }

 apStaticIpRouteGatewayType   OBJECT-TYPE
    SYNTAX      InetAddressType
    MAX-ACCESS  read-only
    STATUS      current
    DESCRIPTION
            "The Internet address type of apStaticIpRouteGateway."
    ::= { apStaticIpRoute 5 }
    
  apStaticIpRouteGateway   OBJECT-TYPE
    SYNTAX      InetAddress
    MAX-ACCESS  read-write
    STATUS      current
    DESCRIPTION
            "Nexthop IP of the static route."
    ::= { apStaticIpRoute 6 }


--*****************************************************************
-- apStaticIPv6Route         OBJECT IDENTIFIER ::= { apGlobalConfig 10 }
--*****************************************************************

 apStaticIPv6RouteDestType   OBJECT-TYPE
    SYNTAX      InetAddressType
    MAX-ACCESS  read-only
    STATUS      current
    DESCRIPTION
            "The Internet address type of apStaticIPv6RouteDest."
    ::= { apStaticIPv6Route 1 }

 apStaticIPv6RouteDest   OBJECT-TYPE
    SYNTAX      InetAddress
    MAX-ACCESS  read-write
    STATUS      current
    DESCRIPTION
            "Destination IPv6 of the static route."
    ::= { apStaticIPv6Route 2 }

 apStaticIPv6PrefixLength   OBJECT-TYPE
    SYNTAX      INTEGER (0..128)
    MAX-ACCESS  read-write
    STATUS      current
    DESCRIPTION
            "Prefix length of IPv6 route destination."
    ::= { apStaticIPv6Route 3 }

 apStaticIPv6RouteGatewayType   OBJECT-TYPE
    SYNTAX      InetAddressType
    MAX-ACCESS  read-only
    STATUS      current
    DESCRIPTION
            "The Internet address type of apStaticIPv6RouteGateway."
    ::= { apStaticIPv6Route 4 }

  apStaticIPv6RouteGateway   OBJECT-TYPE
    SYNTAX      InetAddress
    MAX-ACCESS  read-write
    STATUS      current
    DESCRIPTION
            "Nexthop IPv6 of the static route."
    ::= { apStaticIPv6Route 5 }


--*****************************************************************
--  apBridgeConfig         OBJECT IDENTIFIER ::= { apGlobalConfig 11 }
--*****************************************************************

apBridgeConfigStp OBJECT-TYPE
    SYNTAX      TruthValue
    MAX-ACCESS  read-write
    STATUS      current
    DESCRIPTION
        "Indicates whether the Spanning Tree Protocol(STP) is
         enabled or disabled. STP is supported only for bridge
         interfaces. If user tries to set this value for interfaces
         other then bridge interfaces SNMP Query will timeout."
    DEFVAL      { false }        
    ::= { apBridgeConfig 1 }

apBridgeConfigFd OBJECT-TYPE
    SYNTAX      Integer32(4..30)
    MAX-ACCESS  read-write
    STATUS      current
    DESCRIPTION
            "Interface forwarding delay for bridge interfaces. 
            Only used when STP is enabled."
    DEFVAL { 15 }         
    ::= { apBridgeConfig 2 }

apBridgeConfigHello OBJECT-TYPE
    SYNTAX      Integer32(1..10)
    MAX-ACCESS  read-write
    STATUS      current
    DESCRIPTION
            "Indicates hello time for bridge interfaces. Only used 
            when STP is enabled."
    DEFVAL { 2 }        
    ::= { apBridgeConfig 3 }


--*****************************************************************
-- apFirmwareUpgrade
--*****************************************************************

apFirmwareUpgradeAddressType OBJECT-TYPE
    SYNTAX  InetAddressType
    MAX-ACCESS  read-only
    STATUS  current
    DESCRIPTION
            "The type of the firmware upgrade IP address as defined
             in the InetAddress MIB for upgrading firmware."
    REFERENCE "RFC 3291"
    DEFVAL { unknown }
    ::= { apFirmwareUpgrade 1 }

apFirmwareUpgradeAddress OBJECT-TYPE 	
    SYNTAX  InetAddress
    MAX-ACCESS  read-write
    STATUS  current
    DESCRIPTION
            "The IP address of the server where the 
             firmware file is located."
    ::= { apFirmwareUpgrade 2 }

apFirmwareUpgradePort OBJECT-TYPE 	
    SYNTAX  Integer32(1..65535)
    MAX-ACCESS  read-write
    STATUS  current
    DESCRIPTION
        "Port on the server from which to get the firmware file."
    DEFVAL { 69 }
    ::= { apFirmwareUpgrade 3 }

apFirmwareUpgradeDirectory OBJECT-TYPE
    SYNTAX  DisplayString (SIZE (0..255))
    MAX-ACCESS  read-write
    STATUS  current
    DESCRIPTION
        "Directory on the server from which to get the firmware
         file. The file directory cannot contain the filename.
         This is the full path to file but not the file itself.
         For example, /wireless/ap/config. When all the objects
         are set correctly, the download string is formed as such:
             <TFTP>://<ipAddress>[:<port>]/<fullpath>/<filename.tar>"
    ::= { apFirmwareUpgrade 4 }

apFirmwareDownloadImagename OBJECT-TYPE
    SYNTAX  DisplayString (SIZE (0..64))
    MAX-ACCESS  read-write
    STATUS  current
    DESCRIPTION
        "Firmware file name to upgrade the AP with. The filename
         cannot contain the full path to the directory where the
         file will be placed. When all the objects are set correctly,
         the download string is formed as such:
             <TFTP>://<ipAddress>[:<port>]/<fullpath>/<filename.tar>"
    ::= { apFirmwareUpgrade 5 }

apFirmwareUpgradeProtocol OBJECT-TYPE
    SYNTAX  INTEGER {
        tftp(1)
    }
    MAX-ACCESS  read-only
    STATUS  current
    DESCRIPTION
        "The protocol used for upgrading the AP firmware."
    DEFVAL { tftp }
    ::= { apFirmwareUpgrade 6 }

apFirmwareUpgradeStart OBJECT-TYPE
    SYNTAX  INTEGER {
        enable(1), 
        disable(2)
    }
    MAX-ACCESS  read-write
    STATUS  current
    DESCRIPTION
        "This object initiates the upgrading of firmware on the AP."
    DEFVAL { disable }
    ::= { apFirmwareUpgrade 7 }

apFirmwareImageDownloadStatus OBJECT-TYPE
    SYNTAX  INTEGER {
        transferNotInitiated(1),
        trasferInProgress(2),
        transferFailed(3),
        transferSucceeded(4)
    }
    MAX-ACCESS  read-only
    STATUS  current
    DESCRIPTION
            "Indicates download status of firmware image on AP. 
             The object that initiates the download part
             of the firmware upgrade. The image file is
             to be downloaded onto the AP, then apply the
             firmware validation, then upgrade the firmware."
    DEFVAL { transferNotInitiated }
    ::= { apFirmwareUpgrade 8 }

--*****************************************************************


apFileTransferProtocol OBJECT-TYPE
    SYNTAX  INTEGER {
        tftp(1)
    }
    MAX-ACCESS  read-only
    STATUS  current
    DESCRIPTION
        "The protocol used for transferring a file over the network."
    DEFVAL { tftp }
    ::= { apFileTransfer 1 }

apFileTransferSrcFileType OBJECT-TYPE
    SYNTAX  INTEGER {
      networkFile(1), -- File on another network device
      backupConfig(2),
      mirrorConfig(3),
      runningConfig(4),
      startupConfig(5)
    }
    MAX-ACCESS  read-write
    STATUS  current
    DESCRIPTION
        "Specifies the type of file to copy from. One of apFileTransferSrcFileType
        or apFileTransferDstFileType must be of type backupConfig, mirrorConfig,
        runningConfig, startupConfig. Also apFileTransferSrcFileType must be
        different from apFileTransferDstFileType. 
        
        If the apFileTransferSrcFileType has the value networkFile, the 
        apFileTransferFileType and apFileTransferFileName must also be created."
    ::= { apFileTransfer 2 }

apFileTransferDstFileType OBJECT-TYPE
    SYNTAX  INTEGER {
      networkFile(1),
      backupConfig(2),
      startupConfig(3)
    }
    MAX-ACCESS  read-write
    STATUS  current
    DESCRIPTION
        "Specifies the type of file to copy from. One of apFileTransferSrcFileType
        or apFileTransferDstFileType must be of type backupConfig, mirrorConfig,
        runningConfig, startupConfig. Also apFileTransferSrcFileType must be
        different from apFileTransferDstFileType. 
        
        If the apFileTransferDstFileType has the value networkFile, the 
        apFileTransferFileType and apFileTransferFileName must also be created."
    ::= { apFileTransfer 3 }

apFileTransferFilename OBJECT-TYPE
    SYNTAX  DisplayString (SIZE (1..255))
    MAX-ACCESS  read-write
    STATUS  current
    DESCRIPTION
        "File to be downloaded onto the AP from server. Only xml files
         are allowed to be downloaded. The filename cannot contain the
         full path to the directory where the file will be placed.
             When all the objects are set correctly, the
             download string is formed as such:
             <TFTP>://<ipAddress>[:<port>]/<fullpath>/<filename.xml>. This
         object must be created when either apFileTransferSrcFileType or
         apFileTransferDstFileType has the value networkFile."
    ::= { apFileTransfer 4 }

apFileTransferAddressType OBJECT-TYPE 	
    SYNTAX  InetAddressType
    MAX-ACCESS  read-only
    STATUS  current
    DESCRIPTION
            "The type of the IP address as defined 
             in the InetAddress MIB for transferring a file."
    REFERENCE "RFC 3291"
    DEFVAL { unknown }
    ::= { apFileTransfer 5 }

apFileTransferAddress OBJECT-TYPE 	
    SYNTAX  InetAddress
    MAX-ACCESS  read-write
    STATUS  current
    DESCRIPTION
        "The ip address of the tftp server from (or to) which to copy the 
        configuration file. This object must be created when either the 
        apFileTransferSrcFileType or apFileTransferDstFileType has the 
        value networkFile."
    ::= { apFileTransfer 6 }


apFileTransferPort OBJECT-TYPE
    SYNTAX  Integer32(1..65535)
    MAX-ACCESS  read-write
    STATUS  current
    DESCRIPTION
        "The port of the tftp server from (or to) which to copy the
         configuration file. This object must be created when either the
         apFileTransferSrcFileType or apFileTransferDstFileType has the
         value networkFile."
    DEFVAL { 69 }
    ::= { apFileTransfer 7 }

apFileTransferStart OBJECT-TYPE
    SYNTAX  INTEGER {
        enable(1), 
        disable(2)
    }
    MAX-ACCESS  read-write
    STATUS  current
    DESCRIPTION
        "This object initiates the transferring of file onto the AP.
         This object must be created when either the 
         apFileTransferSrcFileType or apFileTransferDstFileType has the
         value networkFile."
        
    DEFVAL { disable }
    ::= { apFileTransfer 11 }

apFileTransferStatus OBJECT-TYPE
    SYNTAX  INTEGER {
        transferNotInitiated(1),
        wrongFileType(2),
        wrongFileFormat(3),
        trasferInProgress(4),
        transferFailed(5),
        transferSucceeded(6)
    }
    MAX-ACCESS  read-only
    STATUS  current
    DESCRIPTION
            "The current status of the file transfer."
    DEFVAL { transferNotInitiated }
    ::= { apFileTransfer 12 }

apFileTransferValidationStatus OBJECT-TYPE
    SYNTAX  INTEGER {
        validationNotInitiated(1),
        validationInProgress(2),
        validationFailed(3),
        validationSucceeded(4)
    }
    MAX-ACCESS  read-only
    STATUS  current
    DESCRIPTION
        "This object detemines the status of the file validation.
         After the file is successfully transferred onto an AP,
         it is validated to make sure it is in the correct format."
    DEFVAL { validationNotInitiated }
    ::= { apFileTransfer 13 }



--*****************************************************************
-- apLogConfig            OBJECT IDENTIFIER ::= { ciscosbWLANAP 3 }
--*****************************************************************
  
        apLogDepth		OBJECT-TYPE
    SYNTAX	Integer32(1..512)
    MAX-ACCESS read-write
    STATUS current
    DESCRIPTION
        "Maximum number of log messages that are stored in volatile memory"
        DEFVAL          { 512 }                                
        ::= { apLogConfig 1 }

        apLogPersistence	OBJECT-TYPE
    SYNTAX  INTEGER {
    	        notPersistent(0),
    		persistent(1)
            	}
    MAX-ACCESS read-write
    STATUS current
    DESCRIPTION
        "Flag to indicate whether logs will be written to
         non-volatile memory."
        DEFVAL                  { notPersistent }                                 
        ::= { apLogConfig 2 }

        apLogSeverity   	OBJECT-TYPE
    SYNTAX	Integer32(0..7)
    MAX-ACCESS read-write
    STATUS current
    DESCRIPTION
        "Severity level of log messages to write to
         non-volatile memory."
        DEFVAL                  { 7 }                                
        ::= { apLogConfig 3 }

        apLogRelayEnabled    	OBJECT-TYPE
    SYNTAX	INTEGER {
            	disabled(0),
    	        enabled(1)
       	        }
    MAX-ACCESS read-write
    STATUS current
    DESCRIPTION
        "Flag to indicate whether log entries are sent to a
         syslog server."
        DEFVAL          { disabled }
        ::= { apLogConfig 4 }

        apLogRelayHostType   	OBJECT-TYPE
    SYNTAX	InetAddressType
    MAX-ACCESS read-write
    STATUS current
    DESCRIPTION
        "The Internet address type of apLogRelayHost.
         The inet address type must be configured before
         configuring IP address or domain name"

        ::= { apLogConfig 5 }

        apLogRelayHost   	OBJECT-TYPE
    SYNTAX	InetAddress
    MAX-ACCESS read-write
    STATUS current
    DESCRIPTION
        "Hostname or IP address of syslog host.
         The inet address type must be configured before
         configuring IP address or domain name"

        ::= { apLogConfig 6 }

        apLogRelayPort    	OBJECT-TYPE
    SYNTAX	Integer32(1..65535)
    MAX-ACCESS read-write
    STATUS current
    DESCRIPTION
        "Port number of syslog server on relay host."
        DEFVAL                  { 514 }                   
        ::= { apLogConfig 7 }
                                            
-- The apLogEntry Table

apLogTable         OBJECT-TYPE
                        SYNTAX          SEQUENCE OF ApLogEntry
                        MAX-ACCESS      not-accessible
    STATUS        current
                        DESCRIPTION
                        "Log table to display log messages."
    ::={ apLog 2 }

apLogEntry          OBJECT-TYPE
    SYNTAX 	ApLogEntry
    MAX-ACCESS 	not-accessible
    STATUS	current
    DESCRIPTION
                        "Entry in log table."
    INDEX { apLogEntryNumber }
    ::= { apLogTable 1 }

ApLogEntry ::=
        SEQUENCE {
	apLogEntryNumber		Integer32,
	apLogEntryPriority		DisplayString,
	apLogEntryTime			DisplayString,
	apLogEntryDaemon		DisplayString,
	apLogEntryMessage		DisplayString
	}

apLogEntryNumber OBJECT-TYPE
    SYNTAX	 Integer32(0..65535)
    MAX-ACCESS   not-accessible
    STATUS       current
    DESCRIPTION
        "Indicates log entry number in the log table."
        ::= { apLogEntry 1 }

        apLogEntryPriority	OBJECT-TYPE
    SYNTAX	DisplayString
    MAX-ACCESS read-only
    STATUS current
    DESCRIPTION
        "Each log entry can have eight possible priorities.
         Valid values for priority are debug, info, notice,
         warning, error, critical, alert, and emergency."
        ::= { apLogEntry 2 }

        apLogEntryTime   	OBJECT-TYPE
    SYNTAX	DisplayString
    MAX-ACCESS read-only
    STATUS current
    DESCRIPTION
        "Indicates the time when log error message was generated."
        ::= { apLogEntry 3 }

        apLogEntryDaemon    	OBJECT-TYPE
    SYNTAX	DisplayString
    MAX-ACCESS read-only
    STATUS current
    DESCRIPTION
        "Indicates where system log file is located."
        ::= { apLogEntry 4 }

        apLogEntryMessage   	OBJECT-TYPE
    SYNTAX	DisplayString
    MAX-ACCESS read-only
    STATUS current
    DESCRIPTION
        "Log message."
        ::= { apLogEntry 5 }


--*****************************************************************
--  apVap            OBJECT IDENTIFIER ::= { ciscosbWLANAP 4 }
--*****************************************************************

apVapTable	OBJECT-TYPE
        SYNTAX          SEQUENCE OF ApVapEntry
    MAX-ACCESS      not-accessible
        STATUS          current
        DESCRIPTION
	"This table display VAP entries. User can configure sixteen
         Virtual Access Points (VAPs) per radio that simulate
         multiple APs in one physical access point."
    ::= { apVap 1 }

apVapEntry		OBJECT-TYPE
	SYNTAX          ApVapEntry
        MAX-ACCESS      not-accessible
        STATUS          current
	DESCRIPTION
	        "Entry in VAP table."
    INDEX { apVapId, apVapRadio }
    ::= { apVapTable 1 }

ApVapEntry ::=
        SEQUENCE {
         apVapId                OCTET STRING,        
	 apVapRadio		OCTET STRING,
	 apVapStatus		INTEGER,
	 apVapVlanID		Integer32,
	 apVapDescription	DisplayString,
         apVapGlobalRadiusMode  INTEGER,
	 apVapQosMode           INTEGER,
    	 apVapDefBwMaxUp        Integer32,
 	 apVapDefBwMaxDown      Integer32,
    	 apVapAclTypeUp         INTEGER,
    	 apVapAclUp             DisplayString,
    	 apVapAclTypeDown       INTEGER,
    	 apVapAclDown           DisplayString,
    	 apVapPolicyUp          DisplayString,
    	 apVapPolicyDown        DisplayString,
         apVapSchedulerProfile  DisplayString,
         apVapOperationalStatus INTEGER
	 }

apVapId 	OBJECT-TYPE
        SYNTAX	        OCTET STRING (SIZE(0..32))
        MAX-ACCESS      not-accessible
        STATUS          current
        DESCRIPTION
                "The Vap index associated with VAP."
        ::= { apVapEntry 1 }


apVapRadio	OBJECT-TYPE
        SYNTAX	        OCTET STRING (SIZE(0..32))
        MAX-ACCESS      not-accessible
        STATUS          current
        DESCRIPTION
                "The Radio interface index associated with VAP."
        ::= { apVapEntry 2 }

apVapStatus	   OBJECT-TYPE
        SYNTAX	        INTEGER {
                    down(0),
                    up(1)
                    }
        MAX-ACCESS      read-write
        STATUS          current
        DESCRIPTION
        "Indicates administrative status of VAP. Set 'up' to enable
         specified network. If user disables a network,
         VLAN Id is lost."
        ::= { apVapEntry 3 }

apVapVlanID	    OBJECT-TYPE
        SYNTAX          Integer32 (1..4094)
        MAX-ACCESS      read-write
        STATUS          current
        DESCRIPTION
                "VLAN Id associated with VAP."
        DEFVAL    { 1 }               
        ::= { apVapEntry 4 }

apVapDescription    OBJECT-TYPE
        SYNTAX	        DisplayString(SIZE(1..255))
    MAX-ACCESS      read-write
        STATUS          current
        DESCRIPTION
                "Human readable description of each VAP."
        ::= { apVapEntry 5 }
        
   apVapGlobalRadiusMode	OBJECT-TYPE
        SYNTAX	        INTEGER {
                                down(1), 
                                up(2)
                        }
        MAX-ACCESS      read-only
        STATUS          obsolete
        DESCRIPTION
        "This object is moved to BSS Table and should no longer be used."
        DEFVAL          { up }         
        ::= { apVapEntry 6}


   apVapQosMode	OBJECT-TYPE
        SYNTAX	        INTEGER {
                                up(1), 
                                down(0)
                        }
    MAX-ACCESS      read-write
        STATUS          current
        DESCRIPTION
                "Indicates whether qos mode is enabled or not."
        DEFVAL          { down }         
        ::= { apVapEntry 7}      

   apVapDefBwMaxUp	OBJECT-TYPE
        SYNTAX	        Integer32 (0..300)
    MAX-ACCESS      read-write
        STATUS          current
        DESCRIPTION
                "Maximum default bandwidth in up direction in Mbps."
        DEFVAL          { 0 }         
        ::= { apVapEntry 8}      

apVapDefBwMaxDown   OBJECT-TYPE
        SYNTAX	        Integer32 (0..300)
    MAX-ACCESS      read-write
        STATUS          current
        DESCRIPTION
                "Maximum default bandwidth in down direction in Mbps."
        DEFVAL          { 0 }         
        ::= { apVapEntry 9}      

   apVapAclTypeUp	OBJECT-TYPE
        SYNTAX	        INTEGER {
                                none(0), 
                                ipv4(1),
                                ipv6(2), 
                                mac(3)
                        }
    MAX-ACCESS   read-write
        STATUS          current
        DESCRIPTION
                "Indicates the type of ACL in UP direction.This object must
		 be set before setting apVapAclUp object."
        DEFVAL          { none }         
        ::= { apVapEntry 10}      

  apVapAclUp    	OBJECT-TYPE
        SYNTAX	        DisplayString(SIZE(1..32))
    MAX-ACCESS   read-write
        STATUS          current
        DESCRIPTION
                "Human readable name of ACL in UP direction. 
                It should be one of the names in apQosAclName object.apVapAclTypeUp
                object must be set prior to setting this object."
        ::= { apVapEntry 11 }
        
apVapAclTypeDown   OBJECT-TYPE
        SYNTAX	        INTEGER {
                                none(0), 
                                ipv4(1), 
                                ipv6(2), 
                                mac(3)
                        }
    MAX-ACCESS     read-write
        STATUS          current
        DESCRIPTION
                "Indicates the type of ACL in DOWN direction.
                It should be one of the names in apQosAclName object.This object must
                 be set before setting apVapAclDown object."
        DEFVAL          { none }         
        ::= { apVapEntry 12 }      

  apVapAclDown  	OBJECT-TYPE
        SYNTAX	        DisplayString(SIZE(1..32))
    MAX-ACCESS      read-write
        STATUS          current
        DESCRIPTION
                "Human readable name of ACL in DOWN direction.
                It should be one of the names in apQosAclName object.apVapAclTypeDown
                object must be set prior to setting this object."
        ::= { apVapEntry 13 }
        
  apVapPolicyUp  	OBJECT-TYPE
        SYNTAX	        DisplayString(SIZE(1..32))
    MAX-ACCESS      read-write
        STATUS          current
        DESCRIPTION
        "Human readable name of Diffserv Policy in UP direction. 
        It should be one of the names in apQosDsPolicyMapName object."
        ::= { apVapEntry 14 }
        
  apVapPolicyDown     OBJECT-TYPE
        SYNTAX	        DisplayString(SIZE(1..32))
    MAX-ACCESS      read-write
        STATUS          current
        DESCRIPTION
        "Human readable name of Diffserv Policy in DOWN direction.
        It should be one of the names in apQosDsPolicyMapName object."
        ::= { apVapEntry 15 }
        
  apVapSchedulerProfile     OBJECT-TYPE
        SYNTAX	        DisplayString(SIZE(1..32))
    MAX-ACCESS      read-write
        STATUS          current
        DESCRIPTION
        "Scheduler profile name that is associated with this vap.
        This is referenced to the apSchedulerProfileTable."
        ::= { apVapEntry 16 }

  apVapOperationalStatus	   OBJECT-TYPE
        SYNTAX	        INTEGER {
                    down(0),
                    up(1)
                    }
        MAX-ACCESS      read-only
        STATUS          current
        DESCRIPTION
        "Indicates operational status of VAP. The associated Scheduler profile 
        apVapSchedulerProfile could affect this field."
        ::= { apVapEntry 17 }


--*****************************************************************
--  apIfConfig     OBJECT IDENTIFIER ::= { ciscosbWLANAP 5 }
--*****************************************************************

apIfConfigTable   OBJECT-TYPE
    SYNTAX      SEQUENCE OF ApIfConfigEntry
    MAX-ACCESS  not-accessible
    STATUS      current
    DESCRIPTION
            "A list of interface configuration entries."
    ::= { apIfConfig 1 }

apIfConfigEntry OBJECT-TYPE
    SYNTAX      ApIfConfigEntry
    MAX-ACCESS  not-accessible
    STATUS      current
    DESCRIPTION
            "An entry containing configuration information applicable 
	    to a particular interface."
    INDEX   { apIfConfigIndex }
    ::= { apIfConfigTable 1 }

ApIfConfigEntry ::=
    SEQUENCE {
             apIfConfigIndex                    Integer32,    
             apIfConfigName                     DisplayString, 
             apIfConfigType                     DisplayString,
             apIfConfigMacAddress               MacAddress,
             apIfConfigStaticIpType	        InetAddressType,
             apIfConfigStaticIp		        InetAddress,
             apIfConfigStaticMaskType	        InetAddressType,
	     apIfConfigStaticMask	        InetAddress,
             apIfConfigPathcost                 Integer32,         
	     apIfConfigPriority		        Integer32,
	     apIfConfigSsid		        ApSsid,
	     apIfConfigBss		        ApBssId,
	     apIfConfigSecurity		        INTEGER,
	apIfConfigWpaPersonalKey	DisplayString,
	     apIfConfigWepKeyAscii	        TruthValue,
	     apIfConfigWepKeyLength	        INTEGER,
	     apIfConfigWepDefaultKey	        Integer32,
	apIfConfigWepKey1		DisplayString,
	apIfConfigWepKey2		DisplayString,
	apIfConfigWepKey3		DisplayString,
	apIfConfigWepKey4		DisplayString,
	     apIfConfigRadio		        INTEGER,
	     apIfConfigRemoteMac	        MacAddress,
	     apIfConfigWepKey		        OCTET STRING,
	     apIfConfigWdsSsid		        ApSsid,
	     apIfConfigWdsSecPolicy	        INTEGER,
	apIfConfigWdsWpaPskKey	        DisplayString,
             apIfConfigRxBytes                  Integer32, 
             apIfConfigRxPackets                Integer32, 
             apIfConfigRxErrors                 Integer32, 
             apIfConfigTxBytes                  Integer32,
             apIfConfigTxPackets                Integer32,
             apIfConfigTxErrors                 Integer32, 
             apIfConfigTxDropBytes              Integer32,
             apIfConfigRxDropBytes              Integer32,
             apIfConfigTxDropPackets            Integer32,
             apIfConfigRxDropPackets            Integer32,
             apIfConfigGreenEthMode             DisplayString,
       
             apIfConfigTsVoTxBytes              Integer32,
             apIfConfigTsViTxBytes              Integer32,
             apIfConfigTsVoRxBytes              Integer32,
             apIfConfigTsViRxBytes              Integer32,
             apIfConfigTsVoTxPackets            Integer32,
             apIfConfigTsViTxPackets            Integer32,
             apIfConfigTsVoRxPackets            Integer32,
             apIfConfigTsViRxPackets            Integer32
    }
apIfConfigIndex  OBJECT-TYPE
        SYNTAX           Integer32(0..1024)
        MAX-ACCESS       not-accessible
        STATUS           current
        DESCRIPTION
             "Indicates index for the IfConfigTable"
        ::= { apIfConfigEntry 1 }

apIfConfigName           OBJECT-TYPE
        SYNTAX           DisplayString
        MAX-ACCESS       read-only
        STATUS           current
        DESCRIPTION
             "Indicates name of interface."
        ::= { apIfConfigEntry 2 }

apIfConfigType  OBJECT-TYPE
    SYNTAX       DisplayString
                 MAX-ACCESS read-only
                 STATUS current
                 DESCRIPTION
       "Indicates type of interface. Valid values are 'ethernet', 
       'loopback', 'service-set', 'bridge', 'vlan', and 'wds'."
         ::= { apIfConfigEntry 3 }   

apIfConfigMacAddress     OBJECT-TYPE
        SYNTAX           MacAddress
        MAX-ACCESS       read-only
        STATUS           current
        DESCRIPTION
             "Indicates MAC Address of the interface."
        ::= { apIfConfigEntry 4 }

apIfConfigStaticIpType   OBJECT-TYPE
    SYNTAX      InetAddressType
    MAX-ACCESS  read-only
    STATUS      current
    DESCRIPTION
            "The Internet address type of apIfConfigStaticIp."
    ::= { apIfConfigEntry 5 }
       
apIfConfigStaticIp OBJECT-TYPE
    SYNTAX      InetAddress
    MAX-ACCESS  read-write
    STATUS      current
    DESCRIPTION
        "IP address that will be used when DHCP server is disabled."
    ::= { apIfConfigEntry 6 }

apIfConfigStaticMaskType   OBJECT-TYPE
    SYNTAX      InetAddressType
    MAX-ACCESS  read-only
    STATUS      current
    DESCRIPTION
            "The Internet address type of apIfConfigStaticMask."
    ::= { apIfConfigEntry 7 }

apIfConfigStaticMask OBJECT-TYPE
    SYNTAX      InetAddress
    MAX-ACCESS  read-write
    STATUS      current
    DESCRIPTION
        "Netmask that will be used when the DHCP server is disabled."
    ::= { apIfConfigEntry 8 }

apIfConfigPathcost  OBJECT-TYPE
        SYNTAX           Integer32
        MAX-ACCESS       read-write
        STATUS           current
        DESCRIPTION
        "Contribution of this port to the path cost of paths towards
        the spanning tree root which include this port. 802.1D-1990
        recommends that the default value of this parameter be in
        inverse proportion to the speed of the attached LAN."
        ::= { apIfConfigEntry 9 }

apIfConfigPriority OBJECT-TYPE
    SYNTAX	Integer32(0..65535)
    MAX-ACCESS  read-only
    STATUS      current
    DESCRIPTION
            "Interface bridge priority. Only used when STP is enabled."
    DEFVAL { 0 }        
    ::= { apIfConfigEntry 10 }

apIfConfigSsid OBJECT-TYPE
    SYNTAX      ApSsid
    MAX-ACCESS  read-write
    STATUS      current
    DESCRIPTION
        "Indicates the Service Set Id (SSID) associated with this
         interface. Value can be any string 1 to 32 characters."
    ::= { apIfConfigEntry 11 }

apIfConfigBss OBJECT-TYPE
    SYNTAX      ApBssId
    MAX-ACCESS  read-only
    STATUS      current
    DESCRIPTION
        "Indicates the Basic Service Set (BSS) associated with service
        set interface. Also serves as an index to the corresponding
        apBssTable entry. Valid value is the name of an existing
        BSS instance."
    ::= { apIfConfigEntry 12 }

apIfConfigSecurity OBJECT-TYPE
    SYNTAX      INTEGER{
                        plainText(1),
                        staticWep(2),
                        wpaPersonal(3),
                        dot1x(4),
                        wpaEnterprise(5)
                }
    MAX-ACCESS  read-write
    STATUS      current
    DESCRIPTION
        "Indicates security to use for service-set interface.
        Valid values can be 'plainText', 'staticWep', 'dot1x',
        'wpaPersonal', and 'wpaEnterprise'."
    DEFVAL      { plainText }        
    ::= { apIfConfigEntry 13 }

apIfConfigWpaPersonalKey OBJECT-TYPE
    SYNTAX      DisplayString(SIZE(8..63))
    MAX-ACCESS  read-write
    STATUS      current
    DESCRIPTION
        "Pre-shared key for Wireless Protected Access (WPA) personal.
        Only used when security is wpa-personal. Valid value is an
        ASCII string between 8 and 63 characters. Personnal Key
        can only be set for service-set interface."
    ::= { apIfConfigEntry 14 }

apIfConfigWepKeyAscii OBJECT-TYPE
    SYNTAX      TruthValue
    MAX-ACCESS  read-write
    STATUS      current
    DESCRIPTION
        "Indicates whether or not the Wired Equivalent Privacy (WEP)
         Key is in ASCII or HEX for service-set interfaces."
    DEFVAL         { false }
    ::= { apIfConfigEntry 15 }

apIfConfigWepKeyLength OBJECT-TYPE
    SYNTAX      INTEGER{
                forty(40),
                onehundredfour(104)
                }
    MAX-ACCESS  read-write
    STATUS      current
    DESCRIPTION
        "Length of the WEP key for service set interfaces.
        The key length values used by the SNMP do not include the
        initialization vector in the length. On the web UI,
        longer key length values may be shown which include the 24-bit 
        initialization vector. For example, a key length of 40 bits
        (not including initialization vector) is equivalent to a
        key length of 64 bits (with initialization vector)."
    DEFVAL      { onehundredfour }        
    ::= { apIfConfigEntry 16 }

apIfConfigWepDefaultKey OBJECT-TYPE
    SYNTAX      Integer32(1..4)
    MAX-ACCESS  read-write
    STATUS      current
    DESCRIPTION
            "Indicates the WEP key index to use when transmitting. 
        Only used when security is static-wep. Valid value is a number
        between 1 and 4. This field is valid for service-set
        interfaces only."
    DEFVAL {1}          
    ::= { apIfConfigEntry 17 }

apIfConfigWepKey1 OBJECT-TYPE
    SYNTAX      DisplayString
    MAX-ACCESS  read-write
    STATUS      current
    DESCRIPTION
        "Configure WEP key 1 for service-set interfaces. The number of
        characters required for each WEP key depends on how user sets
        'Key Length' and 'Key Type':

        - If Key Length is 40 bits and the Key Type is 'ASCII',
          then each WEP key be 5 characters long.
        - If Key Length is 40 bits and Key Type is 'Hex',
          then each WEP key must be 10 characters long.
        - If Key Length is 104 bits and Key Type is 'ASCII',
          then each WEP Key must be 13 characters long.
        - If Key Length is 104 bits and Key Type is 'Hex',
          then each WEP Key must be 26 characters long."
    ::= { apIfConfigEntry 18 }

apIfConfigWepKey2 OBJECT-TYPE
    SYNTAX      DisplayString
    MAX-ACCESS  read-write
    STATUS      current
    DESCRIPTION
        "Configure WEP key 2 for service-set interfaces. The number of
        characters required for each WEP key depends on how user sets
        'Key Length' and 'Key Type':

        - If Key Length is 40 bits and the Key Type is 'ASCII',
          then each WEP key be 5 characters long.
        - If Key Length is 40 bits and Key Type is 'Hex',
          then each WEP key must be 10 characters long.
        - If Key Length is 104 bits and Key Type is 'ASCII',
          then each WEP Key must be 13 characters long.
        - If Key Length is 104 bits and Key Type is 'Hex',
          then each WEP Key must be 26 characters long."
    ::= { apIfConfigEntry 19 }

apIfConfigWepKey3 OBJECT-TYPE
    SYNTAX      DisplayString
    MAX-ACCESS  read-write
    STATUS      current
    DESCRIPTION
        "Configure WEP key 3 for service-set interfaces. The number of
        characters required for each WEP key depends on how user sets
        'Key Length' and 'Key Type':

        - If Key Length is 40 bits and the Key Type is 'ASCII',
          then each WEP key be 5 characters long.
        - If Key Length is 40 bits and Key Type is 'Hex',
          then each WEP key must be 10 characters long.
        - If Key Length is 104 bits and Key Type is 'ASCII',
          then each WEP Key must be 13 characters long.
        - If Key Length is 104 bits and Key Type is 'Hex',
          then each WEP Key must be 26 characters long."
    ::= { apIfConfigEntry 20 }

apIfConfigWepKey4 OBJECT-TYPE
    SYNTAX      DisplayString
    MAX-ACCESS  read-write
    STATUS      current
    DESCRIPTION
        "Configure WEP key 4 for service set interfaces. The number of
        characters required for each WEP key depends on how user sets
        'Key Length' and 'Key Type':

        - If Key Length is 40 bits and the Key Type is 'ASCII',
          then each WEP key be 5 characters long.
        - If Key Length is 40 bits and Key Type is 'Hex',
          then each WEP key must be 10 characters long.
        - If Key Length is 104 bits and Key Type is 'ASCII',
          then each WEP Key must be 13 characters long.
        - If Key Length is 104 bits and Key Type is 'Hex',
          then each WEP Key must be 26 characters long."
    ::= { apIfConfigEntry 21 }

apIfConfigRadio OBJECT-TYPE
    SYNTAX      INTEGER{
                        wlan0(1),
                        wlan1(2)
                }
    MAX-ACCESS  read-write
    STATUS      current
    DESCRIPTION
        "Radio associated with the WDS interface."
    DEFVAL      { wlan0 }         
    ::= { apIfConfigEntry 22 }

apIfConfigRemoteMac OBJECT-TYPE
    SYNTAX      MacAddress
    MAX-ACCESS  read-write
    STATUS      current
    DESCRIPTION
        "MAC Address of the remote end of the
        Wireless Distributed System (WDS) link."
    ::= { apIfConfigEntry 23 }

apIfConfigWepKey OBJECT-TYPE
    SYNTAX      OCTET STRING
    MAX-ACCESS  read-write
    STATUS      current
    DESCRIPTION
        "Configures WEP key for the WDS link. The number of characters
        required for each WEP key depends on how user sets
        'Key Length' and 'Key Type':

        - If Key Length is 40 bits and the Key Type is 'ASCII',
          then each WEP key be 5 characters long.
        - If Key Length is 40 bits and Key Type is 'Hex',
          then each WEP key must be 10 characters long.
        - If Key Length is 104 bits and Key Type is 'ASCII',
          then each WEP Key must be 13 characters long.
        - If Key Length is 104 bits and Key Type is 'Hex',
          then each WEP Key must be 26 characters long."
    ::= { apIfConfigEntry 24 }

apIfConfigWdsSsid OBJECT-TYPE
    SYNTAX      ApSsid
    MAX-ACCESS  read-write
    STATUS      current
    DESCRIPTION
            "SSID for the WDS link. Also serves as an index to the 
	apSsidTable. SSID should be in the range 2 to 32 characters."
    ::= { apIfConfigEntry 25 }

apIfConfigWdsSecPolicy OBJECT-TYPE
    SYNTAX      INTEGER{
                plainText(1), 
                staticWep(2),
                wpaPersonal(3)
                }                    
    MAX-ACCESS  read-write
    STATUS      current
    DESCRIPTION
        "Indicates which security field to use for WDS interfaces. By
        default security policy is not configured on WDS interfaces."
    ::= { apIfConfigEntry 26 }

apIfConfigWdsWpaPskKey OBJECT-TYPE
    SYNTAX      DisplayString(SIZE(8..63))
    MAX-ACCESS  read-write
    STATUS      current
    DESCRIPTION
        "The WDS Wi-Fi Personnal Access(WPA) PSK key. The key is
        minimum 8 and upto 63 characters long."
    ::= { apIfConfigEntry 27 }      

apIfConfigRxBytes        OBJECT-TYPE
        SYNTAX           Integer32
        MAX-ACCESS       read-only
        STATUS           current
        DESCRIPTION
             "Indicates received bytes."
        ::= { apIfConfigEntry 28 }       

apIfConfigRxPackets      OBJECT-TYPE
        SYNTAX           Integer32
        MAX-ACCESS       read-only
        STATUS           current
        DESCRIPTION
        "Indicates received packets."
        ::= { apIfConfigEntry 29 } 

apIfConfigRxErrors       OBJECT-TYPE
        SYNTAX           Integer32
        MAX-ACCESS       read-only
        STATUS           current
        DESCRIPTION
        "Indicates received packets with errors."
        ::= { apIfConfigEntry 30 } 

apIfConfigTxBytes        OBJECT-TYPE
        SYNTAX           Integer32
        MAX-ACCESS       read-only
        STATUS           current
        DESCRIPTION
             "Indicates transmitted bytes."
        ::= { apIfConfigEntry 31 }       

apIfConfigTxPackets      OBJECT-TYPE
        SYNTAX           Integer32
        MAX-ACCESS       read-only
        STATUS           current
        DESCRIPTION
             "Indicates transmitted packets."
        ::= { apIfConfigEntry 32 } 

apIfConfigTxErrors       OBJECT-TYPE
        SYNTAX           Integer32
        MAX-ACCESS       read-only
        STATUS           current
        DESCRIPTION
             "Indicates transmitted packets with errors."
        ::= { apIfConfigEntry 33 } 
        
apIfConfigTxDropBytes    OBJECT-TYPE
        SYNTAX           Integer32
        MAX-ACCESS       read-only
        STATUS           current
        DESCRIPTION
             "Indicates transmitted bytes that were dropped."
        ::= { apIfConfigEntry 34 } 

apIfConfigRxDropBytes    OBJECT-TYPE
        SYNTAX           Integer32
        MAX-ACCESS       read-only
        STATUS           current
        DESCRIPTION
             "Indicates received bytes that were dropped."
        ::= { apIfConfigEntry 35 } 

apIfConfigTxDropPackets  OBJECT-TYPE
        SYNTAX           Integer32
        MAX-ACCESS       read-only
        STATUS           current
        DESCRIPTION
             "Indicates transmitted packets that were dropped."
        ::= { apIfConfigEntry 36 } 

apIfConfigRxDropPackets  OBJECT-TYPE
        SYNTAX           Integer32
        MAX-ACCESS       read-only
        STATUS           current
        DESCRIPTION
             "Indicates received packets that were dropped."
        ::= { apIfConfigEntry 37 }
 
apIfConfigTsVoTxBytes    OBJECT-TYPE
        SYNTAX           Integer32
        MAX-ACCESS       read-only
        STATUS           current
        DESCRIPTION
             ""
        ::= { apIfConfigEntry 38 } 

apIfConfigTsViTxBytes    OBJECT-TYPE
        SYNTAX           Integer32
        MAX-ACCESS       read-only
        STATUS           current
        DESCRIPTION
             ""
        ::= { apIfConfigEntry 39} 

apIfConfigTsVoRxBytes    OBJECT-TYPE
        SYNTAX           Integer32
        MAX-ACCESS       read-only
        STATUS           current
        DESCRIPTION
             ""
        ::= { apIfConfigEntry 40 } 
apIfConfigTsViRxBytes    OBJECT-TYPE
        SYNTAX           Integer32
        MAX-ACCESS       read-only
        STATUS           current
        DESCRIPTION
             ""
        ::= { apIfConfigEntry 41 } 

apIfConfigTsVoTxPackets  OBJECT-TYPE
        SYNTAX           Integer32
        MAX-ACCESS       read-only
        STATUS           current
        DESCRIPTION
             ""
        ::= { apIfConfigEntry 42 } 
apIfConfigTsViTxPackets  OBJECT-TYPE
        SYNTAX           Integer32
        MAX-ACCESS       read-only
        STATUS           current
        DESCRIPTION
             ""
        ::= { apIfConfigEntry 43 } 

apIfConfigTsVoRxPackets  OBJECT-TYPE
        SYNTAX           Integer32
        MAX-ACCESS       read-only
        STATUS           current
        DESCRIPTION
             ""
        ::= { apIfConfigEntry 44 } 

apIfConfigTsViRxPackets  OBJECT-TYPE
        SYNTAX           Integer32
        MAX-ACCESS       read-only
        STATUS           current
        DESCRIPTION
             ""
        ::= { apIfConfigEntry 45 } 
        
apIfConfigGreenEthMode  OBJECT-TYPE
        SYNTAX          DisplayString
        MAX-ACCESS      read-write
        STATUS          current
        DESCRIPTION
                "Get/Set the Green ethernet mode to (up/down)."
        ::= { apIfConfigEntry 46 }

--*****************************************************************
--      apRadioBss      OBJECT IDENTIFIER ::= { ciscosbWLANAP 6 }                            
--*****************************************************************

apRadioTable OBJECT-TYPE
    SYNTAX      SEQUENCE OF ApRadioEntry
    MAX-ACCESS  not-accessible
    STATUS      current
    DESCRIPTION
            "A list of radio configuration entries."
    ::= { apRadioBss 1 }

apRadioEntry OBJECT-TYPE
    SYNTAX      ApRadioEntry
    MAX-ACCESS  not-accessible
    STATUS      current
    DESCRIPTION
            "An entry containing configuration information applicable 
	     to a particular radio."
    INDEX   { apRadioIdentifier }
    ::= { apRadioTable 1 }

ApRadioEntry ::=
    SEQUENCE {
	apRadioIdentifier           ApRadioId,
	apRadioStatus		    INTEGER,
	apRadioName		    DisplayString,
	apRadioMac		    MacAddress,
        apRadioMaxBss		                Integer32,
	apRadioChannelPolicy	    INTEGER,
	apRadioMode		    INTEGER,
	apRadioDot11h		    TruthValue,
	apRadioDot11d   	    TruthValue,
	apRadioStaticChannel	                Integer32,
	apRadioChannel		                Integer32,
	apRadioTxPower		    INTEGER,
	apRadioBeaconInterval	    Integer32,
	apRadioRtsThreshold	    Integer32,
	apRadioFragThreshold	    Integer32,
	apRadioApDetection	    TruthValue,
	apRadioFrequency	                Integer32,
	apRadioWme		    TruthValue,
	apRadioWmeNoAck		    TruthValue,
	apRadioWmeAPSD		    TruthValue,
	apRadioRateLimitEnable      TruthValue,
	apRadioRateLimit	    Integer32,
	apRadioRateLimitBurst       Integer32, 
        apRadioWlanUtil                         Integer32,
        apRadioChannelBandwidth     INTEGER,
        apRadioPrimaryChannel       INTEGER,
        apRadioShortGuardIntervalSupported   INTEGER,
        apRadioSTBCMode             INTEGER,
        apRadioProtection           INTEGER,
	apRadioFixedMulticastRate   OCTET STRING,
	apRadioNumAssociatedStations   INTEGER,
        apRadioDtimPeriod           Integer32,
	apRadioMaxStations          Integer32,
        apRadioEdcaTemplate         INTEGER,
--	apRadioAntennaDiversity     TruthValue,
--	apRadioAntennaSelection     ApAntennaSel
        apRadioSchedulerProfile     DisplayString,
        apRadioOperationalStatus    INTEGER,
        apRadioOperationalChannelBandwidth     INTEGER,
        apRadioOperationalPrimaryChannel       INTEGER
    }

apRadioIdentifier OBJECT-TYPE
    SYNTAX      ApRadioId
    MAX-ACCESS  not-accessible
    STATUS      current
    DESCRIPTION
            "Unique Radio Id."
    ::= { apRadioEntry 1 }

apRadioStatus OBJECT-TYPE
    SYNTAX      INTEGER {
		up (1),
		down (2)
		}
    MAX-ACCESS  read-write
    STATUS      current
    DESCRIPTION
            "Administrative status of the radio."
    DEFVAL      { up }         
    ::= { apRadioEntry 2 }

apRadioName OBJECT-TYPE
    SYNTAX      DisplayString
    MAX-ACCESS  read-only
    STATUS      current
    DESCRIPTION
            "Description of the radio."
    ::= { apRadioEntry 3 }

apRadioMac OBJECT-TYPE
    SYNTAX      MacAddress
    MAX-ACCESS  read-only
    STATUS      current
    DESCRIPTION
            "MAC address for the radio."
    ::= { apRadioEntry 4 }

apRadioMaxBss OBJECT-TYPE
    SYNTAX      Integer32
    MAX-ACCESS  read-only
    STATUS      current
    DESCRIPTION
            "Maximum number of BSSes or MAC addresses for this radio."
    ::= { apRadioEntry 5 }

apRadioChannelPolicy OBJECT-TYPE
    SYNTAX      INTEGER {
                static(1), 
                best(2)
                }
    MAX-ACCESS  read-write
    STATUS      current
    DESCRIPTION
        "Channel selection policy. Valid values are 'static', 'best'."
    DEFVAL      { best }        
    ::= { apRadioEntry 6 }

apRadioMode OBJECT-TYPE
    SYNTAX      INTEGER{
                        a(1),
                        bg(2),
                        an(3),
                        bgn(4),
                        nonlya(5),
                        nonlyg(6)
                }
    MAX-ACCESS  read-write
    STATUS      current
    DESCRIPTION
            "Wireless mode for this radio."
    ::= { apRadioEntry 7 }

apRadioDot11h OBJECT-TYPE
    SYNTAX      TruthValue
    MAX-ACCESS  read-write
    STATUS      current
    DESCRIPTION
            "Indicates whether or not 802.11h is enabled on this radio."
    ::= { apRadioEntry 8 }

apRadioDot11d OBJECT-TYPE
    SYNTAX      TruthValue
    MAX-ACCESS  read-write
    STATUS      current
    DESCRIPTION
            "Indicates whether or not 802.11d is enabled on the radio."
    DEFVAL      { true }        
    ::= { apRadioEntry 9 }

apRadioStaticChannel OBJECT-TYPE
    SYNTAX      Integer32
    MAX-ACCESS  read-write
    STATUS      current
    DESCRIPTION
            "Specify static channel for this radio."
    ::= { apRadioEntry 10 }

apRadioChannel OBJECT-TYPE
    SYNTAX      Integer32
    MAX-ACCESS  read-only
    STATUS      current
    DESCRIPTION
            "Channel currently in use on this radio."
    ::= { apRadioEntry 11 }

apRadioTxPower OBJECT-TYPE
    SYNTAX      INTEGER{
                low(12),
                medium(25),
                high(50),
                full(100)
    }
    MAX-ACCESS  read-write
    STATUS      current
    DESCRIPTION
        "Current transmit power on this radio.
        Transmit power is specified in percentage."
    DEFVAL      { 100 }        
    ::= { apRadioEntry 12 }

apRadioBeaconInterval OBJECT-TYPE
    SYNTAX      Integer32(20..2000)
    MAX-ACCESS  read-write
    STATUS      current
    DESCRIPTION
            "Base beacon interval for this radio."
    DEFVAL      { 100 }        
    ::= { apRadioEntry 13 }

apRadioRtsThreshold OBJECT-TYPE
    SYNTAX      Integer32(0..2347)
    MAX-ACCESS  read-write
    STATUS      current
    DESCRIPTION
            "Ready to send (RTS) threshold for this radio."
    DEFVAL      { 2347 }        
    ::= { apRadioEntry 14 }

apRadioFragThreshold OBJECT-TYPE
    SYNTAX      Integer32(256..2346)
    MAX-ACCESS  read-write
    STATUS      current
    DESCRIPTION
            "Minimum packet size for fragmentation."
    DEFVAL      { 2346 }
    ::= { apRadioEntry 15 }

apRadioApDetection OBJECT-TYPE
    SYNTAX      TruthValue
    MAX-ACCESS  read-write
    STATUS      current
    DESCRIPTION
            "Whether or not AP detection is enabled."
    DEFVAL      { false }        
    ::= { apRadioEntry 16 }

apRadioFrequency OBJECT-TYPE
    SYNTAX      Integer32
    MAX-ACCESS  read-only
    STATUS      current
    DESCRIPTION
        "Indicates frequency in use on this radio in MHz."
    ::= { apRadioEntry 17 }

apRadioWme OBJECT-TYPE
    SYNTAX      TruthValue
    MAX-ACCESS  read-write
    STATUS      current
    DESCRIPTION
        "Indicates whether Wireless Media Extensions (WME)
        is enabled on this AP."
    DEFVAL    { true }         
    ::= { apRadioEntry 18 }

apRadioWmeNoAck OBJECT-TYPE
    SYNTAX      TruthValue
    MAX-ACCESS  read-write
    STATUS      current
    DESCRIPTION
        "Indicates whether 'No-Acknowledge' option of
             Wireless Media Extensions (WME) is enabled on this AP."
    DEFVAL    { false }         
    ::= { apRadioEntry 19 }

apRadioWmeAPSD OBJECT-TYPE
    SYNTAX      TruthValue
    MAX-ACCESS  read-write
    STATUS      current
    DESCRIPTION
        "Indicates whether Automatic Power Save Delivery (APSD) option
        of Wireless Media Extensions (WME) is enabled on this AP."
    DEFVAL    { true }         
    ::= { apRadioEntry 20 }

apRadioRateLimitEnable OBJECT-TYPE
    SYNTAX      TruthValue
    MAX-ACCESS  read-write
    STATUS      current
    DESCRIPTION
        "Indicates whether broadcast/multicast rate limiting
        is enabled."
    DEFVAL      { false }        
    ::= { apRadioEntry 21 }

apRadioRateLimit OBJECT-TYPE
    SYNTAX      Integer32(1..50)
    MAX-ACCESS  read-write
    STATUS      current
    DESCRIPTION
            "Broadcast/multicast rate limit in packets/second."
    DEFVAL      { 50 }        
    ::= { apRadioEntry 22 }

apRadioRateLimitBurst OBJECT-TYPE
    SYNTAX      Integer32(1..75)
    MAX-ACCESS  read-write
    STATUS      current
    DESCRIPTION
            "Rate limit burst, in packets per second."
    DEFVAL      { 75 }        
    ::= { apRadioEntry 23 }

apRadioWlanUtil         OBJECT-TYPE
    SYNTAX      Integer32
        MAX-ACCESS      read-only
        STATUS          current
        DESCRIPTION             
                "Indicates WLAN utilization of the radio."
        ::= { apRadioEntry 24 }

apRadioChannelBandwidth OBJECT-TYPE
    SYNTAX      INTEGER {
                twentyMHz(1), 
                fortyMHz(2)
                }
    MAX-ACCESS  read-write
    STATUS      current
    DESCRIPTION
            "The channel bandwidth used for 802.11n modes of operation."
    ::= { apRadioEntry 25 }

apRadioPrimaryChannel OBJECT-TYPE
    SYNTAX      INTEGER {
                lower(1), 
                upper(2)
                }
    MAX-ACCESS  read-write
    STATUS      current
    DESCRIPTION
            "The 'primary channel' used in 802.11n 40-MHz channels.
	     The 'primary channel' is one of the two side-by-side
             20-MHz channels which form an 802.11n 40-MHz channel. 
             Beacon Frames are transmitted by the AP on the 'primary
             channel' and legacy stations (non-802.11n) communicate
             with the AP over the 'primary channel'."
    DEFVAL      { lower }        
    ::= { apRadioEntry 26 }

apRadioShortGuardIntervalSupported OBJECT-TYPE
    SYNTAX      INTEGER {
                no(1), 
                yes(2)
                }
    MAX-ACCESS  read-write
    STATUS      current
    DESCRIPTION
            "802.11n allows support for a 'short guard interval'. The
        'guard interval' is an amount of 'dead time' between
        transmission of symbols. Prior to 802.11n, the inter-symbol
        'guard interval' was specified as 800 nanoseconds. 802.11n
        allows for a 'short guard interval' of 400 nanoseconds to
        enhance throughput."
    DEFVAL      { yes }        
    ::= { apRadioEntry 27 }

apRadioSTBCMode OBJECT-TYPE
    SYNTAX      INTEGER {
                off(1), 
                on(2),
                auto(3)
                }
    MAX-ACCESS  read-write
    STATUS      current
    DESCRIPTION
            "Space Time Block Coding (STBC) is an 802.11n transmission 
             technique which improves range and reliability for clients
             having a single antenna."
    DEFVAL      { on }        
    ::= { apRadioEntry 28 }

apRadioProtection OBJECT-TYPE
    SYNTAX      INTEGER {
                auto(1), 
                off(2)
                }
    MAX-ACCESS  read-write
    STATUS      current
    DESCRIPTION
            "Protection is a mechanism defined in later 802.11 standards
	which allow 'legacy' clients/APs to co-exist with the newer
        clients/APs without causing interference, etc. By default,
        this mechanism is typically turned on. However, if network
        administrator is confident that there are no legacy
        clients/APs in the environment, then the Protection mechanism
        can be turned off. This can potentially improve throughput
        in an all 802.11g or all 802.11n network."
    DEFVAL      { auto }        
    ::= { apRadioEntry 29 }

apRadioFixedMulticastRate OBJECT-TYPE
    SYNTAX	OCTET STRING 
    MAX-ACCESS	read-write
    STATUS	current
    DESCRIPTION
	"Specify Fixed Multicast Rate for this radio in Mbps.

        - For radio modes bg, bgn or nonlyg, valid rates are
              auto, 1, 2, 5.5, 6, 9, 11, 12, 18, 24, 36, 48, 54.
        - For radio modes a, an or nonlya mode, valid rates are
              auto, 6, 9, 12, 18, 24, 36, 48, 54."
    ::= { apRadioEntry 30 }

apRadioDtimPeriod OBJECT-TYPE
    SYNTAX      Integer32(1..255) 
    MAX-ACCESS  read-write
    STATUS      current
    DESCRIPTION
      "Delivery Traffic Indication Map (DTIM) period for this Radio."
    DEFVAL      { 2 }        
    ::= { apRadioEntry 31 }

apRadioMaxStations OBJECT-TYPE
    SYNTAX      Integer32(0..200)
    MAX-ACCESS  read-write
    STATUS      current
    DESCRIPTION
            "The maximum number of associations supported."
    DEFVAL      { 200 }        
    ::= { apRadioEntry 32 }

apRadioNumAssociatedStations OBJECT-TYPE
    SYNTAX      INTEGER
    MAX-ACCESS      read-only
    STATUS          current
    DESCRIPTION             
        "Indicates total number of stations associated to this radio."
    ::= { apRadioEntry 33 }

apRadioEdcaTemplate OBJECT-TYPE
    SYNTAX      INTEGER {
                custom(1), 
                default(2),
                voiceOptimized(3)
                }
    MAX-ACCESS  read-write
    STATUS      current
    DESCRIPTION
            "Enables the administrator to set the WMM queue parameters to 
            predefined values."
    DEFVAL      { custom }        
    ::= { apRadioEntry 34 }


-- apRadioAntennaDiversity OBJECT-TYPE
--    SYNTAX      TruthValue
--    MAX-ACCESS  read-write
--    STATUS      current
--    DESCRIPTION
--           "Indicates whether or not antenna diversity is enabled."
--    DEFVAL      { true }        
--    ::= { apRadioEntry 35}

-- apRadioAntennaSelection OBJECT-TYPE
--    SYNTAX      ApAntennaSel
--    MAX-ACCESS  read-write
--    STATUS      current
--    DESCRIPTION
--        "The WLAN chip has 3 RF chains which can be connected to 3
--        antennas. If Antenna-Diversity is enabled, antenna-selection
--        would not have any effect. Disabling Antenna-Diversity allows
--        selection of 2 out of 3 antennas. Valid combinations for
--        antenna selection are leftAndright, leftAndmiddle, middleAndright."
--    DEFVAL      {1}        
--    ::= { apRadioEntry 36 }
-- apRadioStaticChannel	Channel to use when channel-policy is static

  apRadioSchedulerProfile     OBJECT-TYPE
        SYNTAX	        DisplayString(SIZE(1..32))
    MAX-ACCESS      read-write
        STATUS          current
        DESCRIPTION
        "Scheduler profile name that is associated with the radio.
        This is reference to the apSchedulerProfileTable."
        ::= { apRadioEntry 35 }

  apRadioOperationalStatus	   OBJECT-TYPE
        SYNTAX	        INTEGER {
                    down(0),
                    up(1)
                    }
        MAX-ACCESS      read-only
        STATUS          current
        DESCRIPTION
        "Indicates operational status of Radio. The associated Scheduler profile 
        apRadioSchedulerProfile could affect this field."
        ::= { apRadioEntry 36 }

  apRadioOperationalChannelBandwidth OBJECT-TYPE
    SYNTAX      INTEGER {
                twentyMHz(1), 
                fortyMHz(2)
                }
    MAX-ACCESS  read-only
    STATUS      current
    DESCRIPTION
            "The operational channel bandwidth."
    ::= { apRadioEntry 37 }

  apRadioOperationalPrimaryChannel OBJECT-TYPE
    SYNTAX      INTEGER {
                lower(1), 
                upper(2),
		notapplicable(3)  
                }
    MAX-ACCESS  read-only
    STATUS      current
    DESCRIPTION
            "The 'Operational primary channel' used in 802.11n 40-MHz channels.
	     'not applicable' is shown when it is not 40-MHz channel.
	     The 'primary channel' is one of the two side-by-side
             20-MHz channels which form an 802.11n 40-MHz channel. 
             Beacon Frames are transmitted by the AP on the 'primary
             channel' and legacy stations (non-802.11n) communicate
             with the AP over the 'primary channel'."
    ::= { apRadioEntry 38 }


-- *****************************************************************
--   BSS Table
-- *****************************************************************

apBssTable OBJECT-TYPE
    SYNTAX      SEQUENCE OF ApBssEntry
    MAX-ACCESS  not-accessible
    STATUS      current
    DESCRIPTION
            "A list of radio configuration entries."
    ::= { apRadioBss 2 }

apBssEntry OBJECT-TYPE
    SYNTAX      ApBssEntry
    MAX-ACCESS  not-accessible
    STATUS      current
    DESCRIPTION
            "An entry containing configuration information applicable 
	    to a particular Basic Service Set (BSS) Id."
    INDEX   { apBssIdentifier }
    ::= { apBssTable 1 }

ApBssEntry ::=
    SEQUENCE {
	 apBssIdentifier                ApBssId,
	 apBssStatus		        INTEGER,
	 apBssDescr		        DisplayString,
	 apBssRadio		        INTEGER,
	 apBssBeaconInterface           DisplayString,
	 apBssMac		        MacAddress,
	 apBssDtimPeriod	        Integer32,
         apBssMaxStations               Integer32,
         apBssIgnoreBcastSsid	        TruthValue,
	 apBssMacAclMode	        INTEGER,
	 apBssMacAclName	        DisplayString,
	 apBssRadiusAccounting		TruthValue,
	 apBssRadiusIpType              InetAddressType,
	 apBssRadiusPrimaryServerIp	     InetAddress,
	 apBssRadiusBackuponeServerIpType    InetAddressType,
         apBssRadiusBackuponeServerIp        InetAddress,
	 apBssRadiusBackuptwoServerIpType    InetAddressType,
         apBssRadiusBackuptwoServerIp        InetAddress,
	 apBssRadiusBackupthreeServerIpType  InetAddressType,
         apBssRadiusBackupthreeServerIp      InetAddress, 
	 apBssRadiusPrimaryServerIPv6Type    InetAddressType,
         apBssRadiusPrimaryServerIPv6        InetAddress,
	 apBssRadiusBackuponeServerIPv6Type  InetAddressType,
         apBssRadiusBackuponeServerIPv6      InetAddress,
	 apBssRadiusBackuptwoServerIPv6Type  InetAddressType,
         apBssRadiusBackuptwoServerIPv6      InetAddress,
	 apBssRadiusBackupthreeServerIPv6Type InetAddressType,
         apBssRadiusBackupthreeServerIPv6    InetAddress,
        apBssRadiusCurrentServer                DisplayString,
	apBssRadiusPrimaryServerKey             DisplayString,
        apBssRadiusBackuponeServerKey           DisplayString,
        apBssRadiusBackuptwoServerKey           DisplayString,
        apBssRadiusBackupthreeServerKey         DisplayString,
        apBssOpenSystemAuth                     TruthValue,
	 apBssSharedKeyAuth             TruthValue,
	apBssWpaCipherTkip                      TruthValue,
	apBssWpaCipherCcmp                      TruthValue,
	 apBssWpaAllowed	        TruthValue,
	apBssWpa2Allowed                        TruthValue,
	 apBssRsnPreauth	        TruthValue,
         apBssBroadcastKeyRefreshRate   Integer32,
	 apBssSessionKeyRefreshRate     Integer32,
         apBssGlobalRadiusMode          INTEGER,
         apBssMacAclAuthType	        INTEGER,
         apBssStationIsolation          TruthValue
    }

apBssIdentifier OBJECT-TYPE
    SYNTAX      ApBssId
    MAX-ACCESS  not-accessible
    STATUS      current
    DESCRIPTION
            "Unique Id for this BSS."
    ::= { apBssEntry 1 }

apBssStatus OBJECT-TYPE
    SYNTAX	INTEGER {
                        up (1),
		down (2)
		}     
    MAX-ACCESS  read-write
    STATUS      current
    DESCRIPTION
            "Status of this BSS."
    ::= { apBssEntry 2 }

apBssDescr OBJECT-TYPE
    SYNTAX      DisplayString(SIZE(0..64))
    MAX-ACCESS  read-write
    STATUS      current
    DESCRIPTION
            "Human readable description of this BSS."
    ::= { apBssEntry 3 }

apBssRadio OBJECT-TYPE
    SYNTAX      INTEGER{
                        wlan0(1),
                        wlan1(2)
                }      
    MAX-ACCESS  read-only
    STATUS      current
    DESCRIPTION
            "Radio associated with this BSS. Can be used to access
	    the apRadioTable."
    ::= { apBssEntry 4 }

apBssBeaconInterface OBJECT-TYPE
    SYNTAX     DisplayString 
    MAX-ACCESS  read-only
    STATUS      current
    DESCRIPTION
            "Interface used for beacons."
    ::= { apBssEntry 5 }

apBssMac OBJECT-TYPE
    SYNTAX      MacAddress
    MAX-ACCESS  read-only
    STATUS      current
    DESCRIPTION
            "MAC address associated with this BSS."
    ::= { apBssEntry 6 }

apBssDtimPeriod OBJECT-TYPE
    SYNTAX      Integer32(1..255) 
    MAX-ACCESS  read-only
    STATUS      obsolete
    DESCRIPTION
            "This object is moved to Radio Table and should no longer be used."
    DEFVAL      { 2 }        
    ::= { apBssEntry 7 }

apBssMaxStations OBJECT-TYPE
    SYNTAX      Integer32(0..200)
    MAX-ACCESS  read-only
    STATUS      obsolete
    DESCRIPTION
            "This object is moved to Radio Table and should no longer be used."
    DEFVAL      { 200 }        
    ::= { apBssEntry 8 }

apBssIgnoreBcastSsid OBJECT-TYPE
    SYNTAX      TruthValue
    MAX-ACCESS  read-write
    STATUS      current
    DESCRIPTION
        "When true, SSIDs are not sent in beacons and
        probes are ignored."
    DEFVAL      { false }        
    ::= { apBssEntry 9 }

apBssMacAclMode OBJECT-TYPE
    SYNTAX      INTEGER{
                denyList(1),
                acceptList(2)        
                }         
    MAX-ACCESS  read-write
    STATUS      current
    DESCRIPTION
            "Mode for the MAC access list."
    DEFVAL      { denyList }        
    ::= { apBssEntry 10 }

apBssMacAclName OBJECT-TYPE
    SYNTAX      DisplayString
    MAX-ACCESS  read-only
    STATUS      current
    DESCRIPTION
            "MAC ACL name from the existing list of MAC ACL instances."
    ::= { apBssEntry 11 }

apBssRadiusAccounting OBJECT-TYPE
    SYNTAX      TruthValue
    MAX-ACCESS  read-write
    STATUS      current
    DESCRIPTION
        "Indicates whether RADIUS accounting is enabled. User should
        disable global radius server mode (object apBssGlobalRadiusMode
        under BSS table) to set the RADIUS accounting mode associated
        with this BSS. This field is applicable for security types
        that authenticate using RADIUS."
    DEFVAL      { false }        
    ::= { apBssEntry 12 }

apBssRadiusIpType OBJECT-TYPE
    SYNTAX      InetAddressType
    MAX-ACCESS  read-write
    STATUS      current
    DESCRIPTION
            "Type of the IP address associated with this BSS."
    DEFVAL      { ipv4 }        
    ::= { apBssEntry 13 }

apBssRadiusPrimaryServerIp OBJECT-TYPE
    SYNTAX      InetAddress
    MAX-ACCESS  read-write
    STATUS      current
    DESCRIPTION
        "Primary RADIUS server IP address associated with this BSS.
        User should disable global radius server mode (object
        apBssGlobalRadiusMode under BSS table) to configure RADIUS
        server IP address associated with this BSS. This field is
        applicable for security types that authenticate using RADIUS."
    ::= { apBssEntry 14 }

apBssRadiusBackuponeServerIpType OBJECT-TYPE
    SYNTAX      InetAddressType
    MAX-ACCESS  read-only
    STATUS      current
    DESCRIPTION
            "Type of the IP address associated with this BSS."
    ::= { apBssEntry 15 }

apBssRadiusBackuponeServerIp OBJECT-TYPE
    SYNTAX      InetAddress
    MAX-ACCESS  read-write
    STATUS      current
    DESCRIPTION
        "First backup RADIUS server IP address associated with this
        BSS. User should disable global radius server mode (object
        apBssGlobalRadiusMode under BSS table) to configure RADIUS
        server IP address associated with this BSS. This field is
        applicable for security types that authenticate using RADIUS."
    ::= { apBssEntry 16 }

apBssRadiusBackuptwoServerIpType OBJECT-TYPE
    SYNTAX      InetAddressType
    MAX-ACCESS  read-only
    STATUS      current
    DESCRIPTION
            "Type of the IP address associated with this BSS."
    ::= { apBssEntry 17 }

apBssRadiusBackuptwoServerIp OBJECT-TYPE
    SYNTAX      InetAddress
    MAX-ACCESS  read-write
    STATUS      current
    DESCRIPTION
        "Second backup RADIUS server IP address associated with this
        BSS. User should disable global radius server mode (object
        apBssGlobalRadiusMode under BSS table) to configure RADIUS
        server IP address associated with this BSS. This field is
        applicable for security types that authenticate using RADIUS."
    ::= { apBssEntry 18 }

apBssRadiusBackupthreeServerIpType OBJECT-TYPE
    SYNTAX      InetAddressType
    MAX-ACCESS  read-only
    STATUS      current
    DESCRIPTION
            "Type of the IP address associated with this BSS."
    ::= { apBssEntry 19 }

apBssRadiusBackupthreeServerIp OBJECT-TYPE
    SYNTAX      InetAddress
    MAX-ACCESS  read-write
    STATUS      current
    DESCRIPTION
        "Third backup RADIUS server IP address associated with this
        BSS. User should disable global radius server mode (object
        apBssGlobalRadiusMode under BSS table) to configure RADIUS
        server IP address associated with this BSS. This field is
        applicable for security types that authenticate using RADIUS."
    ::= { apBssEntry 20 }

apBssRadiusPrimaryServerIPv6Type   OBJECT-TYPE
    SYNTAX      InetAddressType
    MAX-ACCESS  read-only
    STATUS      current
    DESCRIPTION
            "The Internet address type of apBssRadiusPrimaryServerIPv6."
    ::= { apBssEntry 21 }

apBssRadiusPrimaryServerIPv6 OBJECT-TYPE
    SYNTAX      InetAddress
    MAX-ACCESS  read-write
    STATUS      current
    DESCRIPTION
        "Primary RADIUS IPv6 address associated with this BSS.
        User should disable global radius server mode (object
        apBssGlobalRadiusMode under BSS table) to configure RADIUS
        server IPv6 address associated with this BSS. This field is
        applicable for security types that authenticate using RADIUS."
    ::= { apBssEntry 22 }

apBssRadiusBackuponeServerIPv6Type   OBJECT-TYPE
    SYNTAX      InetAddressType
    MAX-ACCESS  read-only
    STATUS      current
    DESCRIPTION
    "The Internet address type of apBssRadiusBackuponeServerIPv6."
    ::= { apBssEntry 23 }

apBssRadiusBackuponeServerIPv6 OBJECT-TYPE
    SYNTAX      InetAddress
    MAX-ACCESS  read-write
    STATUS      current
    DESCRIPTION
        "First backup RADIUS IPv6 address associated with this BSS.
        User should disable global radius server mode (object
        apBssGlobalRadiusMode under BSS table) to configure RADIUS
        server IPv6 address associated with this BSS. This field is
        applicable for security types that authenticate using RADIUS."
    ::= { apBssEntry 24 }

apBssRadiusBackuptwoServerIPv6Type   OBJECT-TYPE
    SYNTAX      InetAddressType
    MAX-ACCESS  read-only
    STATUS      current
    DESCRIPTION
    "The Internet address type of apBssRadiusBackuptwoServerIPv6."
    ::= { apBssEntry 25 }

apBssRadiusBackuptwoServerIPv6 OBJECT-TYPE
    SYNTAX      InetAddress
    MAX-ACCESS  read-write
    STATUS      current
    DESCRIPTION
        "Second backup RADIUS IPv6 address associated with this BSS.
        User should disable global radius server mode (object
        apBssGlobalRadiusMode under BSS table) to configure RADIUS
        server IPv6 address associated with this BSS. This field is
        applicable for security types that authenticate using RADIUS."
    ::= { apBssEntry 26 }

apBssRadiusBackupthreeServerIPv6Type   OBJECT-TYPE
    SYNTAX      InetAddressType
    MAX-ACCESS  read-only
    STATUS      current
    DESCRIPTION
        "Internet address type of apBssRadiusBackupthreeServerIPv6."
    ::= { apBssEntry 27 }

apBssRadiusBackupthreeServerIPv6 OBJECT-TYPE
    SYNTAX      InetAddress
    MAX-ACCESS  read-write
    STATUS      current
    DESCRIPTION
        "Third backup RADIUS IPv6 address associated with this BSS.
        User should disable global radius server mode (object
        apBssGlobalRadiusMode under BSS table) to configure RADIUS
        server IPv6 address associated with this BSS. This field is
        applicable for security types that authenticate using RADIUS."
    ::= { apBssEntry 28 }

apBssRadiusCurrentServer OBJECT-TYPE
    SYNTAX      DisplayString(SIZE(1..64)) 
    MAX-ACCESS  read-write
    STATUS      current
    DESCRIPTION
       "Current RADIUS server is the radius server currently in use.  
        User can configure this value as primary, backupone, backuptwo
        or backupthree. This parameter is not saved across reboots.
        This field is always set to primary upon bootup. The radius
        current server is set to a valid radius server. The radius
        current is set to primary to start with and if this not valid
        current value is changed to one of valid backupone, backuptwo
        and backupthree in that order and radius current property is
        updated accordingly."
    ::= { apBssEntry 29 }

apBssRadiusPrimaryServerKey OBJECT-TYPE
    SYNTAX      DisplayString(SIZE(1..64))
    MAX-ACCESS  read-write
    STATUS      current
    DESCRIPTION
        "Key for communicating with Primary RADIUS server. User should
        disable global radius server mode (object apBssGlobalRadiusMode
        under BSS table) to configure RADIUS key associated with this
        BSS. This field is applicable for security types that
        authenticate using RADIUS."
    ::= { apBssEntry 30 }

apBssRadiusBackuponeServerKey OBJECT-TYPE
    SYNTAX      DisplayString(SIZE(1..64))
    MAX-ACCESS  read-write
    STATUS      current
    DESCRIPTION
        "Key for communicating with first backup RADIUS server. User
        should disable global radius server mode (object
        apBssGlobalRadiusMode under BSS table) to configure RADIUS key
        associated with this BSS. This field is applicable for
        security types that authenticate using RADIUS."
    ::= { apBssEntry 31 }

apBssRadiusBackuptwoServerKey OBJECT-TYPE
    SYNTAX      DisplayString(SIZE(1..64))
    MAX-ACCESS  read-write
    STATUS      current
    DESCRIPTION
        "Key for communicating with second backup RADIUS server. User
        should disable global radius server mode (object
        apBssGlobalRadiusMode under BSS table) to configure RADIUS key
        associated with this BSS. This field is applicable for
        security types that authenticate using RADIUS."
    ::= { apBssEntry 32 }

apBssRadiusBackupthreeServerKey OBJECT-TYPE
    SYNTAX      DisplayString(SIZE(1..64))
    MAX-ACCESS  read-write
    STATUS      current
    DESCRIPTION
        "Key for communicating with third backup RADIUS server. User
        should disable global radius server mode (object
        apBssGlobalRadiusMode under BSS table) to configure RADIUS key
        associated with this BSS. This field is applicable for
        security types that authenticate using RADIUS."
    ::= { apBssEntry 33 }

apBssOpenSystemAuth OBJECT-TYPE
    SYNTAX      TruthValue
    MAX-ACCESS  read-write
    STATUS      current
    DESCRIPTION
        "Indicates whether Open System authentication is permitted."
    DEFVAL      { true }        
    ::= { apBssEntry 34 }

apBssSharedKeyAuth OBJECT-TYPE
    SYNTAX      TruthValue
    MAX-ACCESS  read-write
    STATUS      current
    DESCRIPTION
        "Indicates whether Shared Key authentication is permitted."
    DEFVAL      { false }        
    ::= { apBssEntry 35 }

apBssWpaCipherTkip OBJECT-TYPE
    SYNTAX      TruthValue
    MAX-ACCESS  read-write
    STATUS      current
    DESCRIPTION
        "Indicates whether Temporal Key Integral Protocol (TKIP)
        is permitted as a WPA cipher."
    DEFVAL      { true }        
    ::= { apBssEntry 36 }

apBssWpaCipherCcmp OBJECT-TYPE
    SYNTAX      TruthValue
    MAX-ACCESS  read-write
    STATUS      current
    DESCRIPTION
        "Indicates whether CCMP is permitted as a WPA cipher."
    DEFVAL      { true }        
    ::= { apBssEntry 37 }

apBssWpaAllowed OBJECT-TYPE
    SYNTAX      TruthValue
    MAX-ACCESS  read-write
    STATUS      current
    DESCRIPTION
        "Indicates whether WPA is allowed."
    DEFVAL      { true }        
    ::= { apBssEntry 38 }

apBssWpa2Allowed OBJECT-TYPE
    SYNTAX      TruthValue
    MAX-ACCESS  read-write
    STATUS      current
    DESCRIPTION
        "Indicates whether WPA2 is allowed."
    DEFVAL      { true }        
    ::= { apBssEntry 39 }

apBssRsnPreauth OBJECT-TYPE
    SYNTAX      TruthValue
    MAX-ACCESS  read-write
    STATUS      current
    DESCRIPTION
        "Indicates whether Robust Secure Network (RSN)
            preauthentication is allowed."
    DEFVAL      { true }        
    ::= { apBssEntry 40 }    

 apBssBroadcastKeyRefreshRate  OBJECT-TYPE
     SYNTAX      Integer32 (0..86400)
     MAX-ACCESS  read-write
     STATUS      current
     DESCRIPTION
        "Specifies the interval after which the broadcast keys
        are changed."
     DEFVAL      { 300 }
     ::= { apBssEntry 41 }

 apBssSessionKeyRefreshRate   OBJECT-TYPE
     SYNTAX      Integer32 
     MAX-ACCESS  read-write
     STATUS      current
     DESCRIPTION
             "Session key refresh rate.The valid range is 30-86400.A value of 0 indicates session key refresh is disabled"
     DEFVAL      { 0 }
     ::= { apBssEntry 42 }

   apBssGlobalRadiusMode	OBJECT-TYPE
        SYNTAX	        INTEGER {
                                down(1), 
                                up(2)
                        }
    MAX-ACCESS      read-write
        STATUS          current
        DESCRIPTION
        "Indicates whether global radius server settings are used."
        DEFVAL          { up }         
        ::= { apBssEntry 43}

   apBssMacAclAuthType	OBJECT-TYPE
        SYNTAX      INTEGER {
                             disable(1),
                             local(2),
                             radius(3)
                    }	
        MAX-ACCESS  read-write
        STATUS      current
        DESCRIPTION
        " Type to disable, enable and specify a lookup method, for
          authentication via client MAC address. Supported types are disable, local, radius"
        DEFVAL          { disable }         
        ::= { apBssEntry 44 }

 apBssStationIsolation OBJECT-TYPE
    SYNTAX      TruthValue
    MAX-ACCESS  read-write
    STATUS      current
    DESCRIPTION
        "Indicates whether stations are isolated from one another in the vap."
    DEFVAL      { false }        
    ::= { apBssEntry 45 }

-- *****************************************************************
--  EDCA AP Table
-- *****************************************************************

apEDCAAPTable OBJECT-TYPE
    SYNTAX      SEQUENCE OF ApEDCAAPEntry
    MAX-ACCESS  not-accessible
    STATUS      current
    DESCRIPTION
       "This table contains the Enhanced Distributed Channel Access (EDCA)
	parameters. 'AP' EDCA parameters affect downstream traffic 
	from the AP to the client station."

    ::= { apRadioBss 3 }

apEDCAAPEntry OBJECT-TYPE
    SYNTAX      ApEDCAAPEntry 
    MAX-ACCESS  not-accessible
    STATUS      current
    DESCRIPTION
       "Contains the 'AP' Enhanced Distributed Channel Access (EDCA)
	parameters for one radio. "
    INDEX { apEDCAAPRadioId, apEDCAAPQueueId }
    ::= { apEDCAAPTable 1 }

ApEDCAAPEntry ::= 
    SEQUENCE {
     apEDCAAPRadioId			ApRadioId,
     apEDCAAPQueueId			INTEGER,
     apEDCAAPAIFS              		INTEGER,
     apEDCAAPMinContentionWindow	INTEGER,
     apEDCAAPMaxContentionWindow	INTEGER,
     apEDCAAPMaxBurst			DisplayString
}

apEDCAAPRadioId OBJECT-TYPE 
     SYNTAX 	 ApRadioId
     MAX-ACCESS  not-accessible
     STATUS      current
     DESCRIPTION
         "Unique Radio ID."
     ::= { apEDCAAPEntry 1 }

apEDCAAPQueueId OBJECT-TYPE 
     SYNTAX 	 INTEGER {
                    voice(0),
                    video(1),
                    besteffort(2),
                    background(3)
                  }
     MAX-ACCESS  read-only
     STATUS      current
     DESCRIPTION
         "ID for this queue."
     ::= { apEDCAAPEntry 2 }

apEDCAAPAIFS   OBJECT-TYPE 
     SYNTAX      INTEGER(1..255)
     MAX-ACCESS  read-write
     STATUS      current
     DESCRIPTION 
         "Specifies the wait time for data frames in msec."
     ::= { apEDCAAPEntry 3 }

apEDCAAPMinContentionWindow OBJECT-TYPE 
     SYNTAX      INTEGER {
                     one(1),
                     three(3),
                     seven(7),
                     fifteen(15),
                     thirty-one(31),
                     sixty-three(63),
                     onetwenty-seven(127),
                     twofifty-five(255),
                     fivehundred-eleven(511),
                     onethousand-twentythree(1023)
                 }
     MAX-ACCESS  read-write
     STATUS      current
     DESCRIPTION
         "Specifies the lower limit of a range from
         which the initial random backoff wait time is
         determined."
     ::= { apEDCAAPEntry 4 }

apEDCAAPMaxContentionWindow OBJECT-TYPE 
     SYNTAX      INTEGER {
                     one(1),
                     three(3),
                     seven(7),
                     fifteen(15),
                     thirty-one(31),
                     sixty-three(63),
                     onetwenty-seven(127),
                     twofifty-five(255),
                     fivehundred-eleven(511),
                     onethousand-twentythree(1023)
                 }
     MAX-ACCESS  read-write
     STATUS      current
     DESCRIPTION
         "Specifies the upper limit of a range from
         which the initial random backoff wait time is
         determined."
     ::= { apEDCAAPEntry 5 }

apEDCAAPMaxBurst OBJECT-TYPE 
     SYNTAX      DisplayString
     MAX-ACCESS  read-write
     STATUS      current
     DESCRIPTION
         "Specifies the maximum burst length (as either an
          integer or floating point value) allowed for
          packet bursts on the wireless network."
     ::= { apEDCAAPEntry 6 }


-- *****************************************************************
--  EDCA Station Table
-- *****************************************************************

apEDCAStationTable OBJECT-TYPE
    SYNTAX      SEQUENCE OF ApEDCAStationEntry
    MAX-ACCESS  not-accessible
    STATUS      current
    DESCRIPTION
       "This table contains the Enhanced Distributed Channel Access (EDCA)
        parameters. 'Station' EDCA parameters affect upstream traffic 
        from the client station to an AP."
    ::= { apRadioBss 4 }

apEDCAStationEntry OBJECT-TYPE
    SYNTAX      ApEDCAStationEntry 
    MAX-ACCESS  not-accessible
    STATUS      current
    DESCRIPTION
       "Contains the Station Enhanced Distributed Channel Access (EDCA)
        parameters for one radio. "
    INDEX { apEDCAStationRadioId, apEDCAStationQueueId }
    ::= { apEDCAStationTable 1 }

ApEDCAStationEntry ::= 
    SEQUENCE {
     apEDCAStationRadioId               ApRadioId,
     apEDCAStationQueueId               INTEGER,
     apEDCAStationAIFS             	INTEGER,
     apEDCAStationMinContentionWindow	INTEGER,
     apEDCAStationMaxContentionWindow	INTEGER,
     apEDCAStationTxOpLimit		INTEGER
}

apEDCAStationRadioId OBJECT-TYPE 
     SYNTAX 	 ApRadioId
     MAX-ACCESS  not-accessible
     STATUS      current
     DESCRIPTION
         "Unique Radio ID."
     ::= { apEDCAStationEntry 1 }

apEDCAStationQueueId OBJECT-TYPE 
     SYNTAX 	 INTEGER {
                    voice(0),
                    video(1),
                    besteffort(2),
                    background(3)
                  }
     MAX-ACCESS  read-only
     STATUS      current
     DESCRIPTION
         "ID for this queue."
     ::= { apEDCAStationEntry 2 }

apEDCAStationAIFS OBJECT-TYPE 
     SYNTAX      INTEGER(1..255)
     MAX-ACCESS  read-write
     STATUS      current
     DESCRIPTION 
         "Specifies the wait time for data frames in msec."
     ::= { apEDCAStationEntry 3 }

apEDCAStationMinContentionWindow OBJECT-TYPE 
     SYNTAX      INTEGER {
                     one(1),
                     three(3),
                     seven(7),
                     fifteen(15),
                     thirty-one(31),
                     sixty-three(63),
                     onetwenty-seven(127),
                     twofifty-five(255),
                     fivehundred-eleven(511),
                     onethousand-twentythree(1023)
                 }
     MAX-ACCESS  read-write
     STATUS      current
     DESCRIPTION
         "Specifies the lower limit of a range from
         which the initial random backoff wait time is
         determined."
     ::= { apEDCAStationEntry 4 }

apEDCAStationMaxContentionWindow OBJECT-TYPE 
     SYNTAX      INTEGER {
                     one(1),
                     three(3),
                     seven(7),
                     fifteen(15),
                     thirty-one(31),
                     sixty-three(63),
                     onetwenty-seven(127),
                     twofifty-five(255),
                     fivehundred-eleven(511),
                     onethousand-twentythree(1023)
                 }
     MAX-ACCESS  read-write
     STATUS      current
     DESCRIPTION
         "Specifies the upper limit of a range from
         which the initial random backoff wait time is
         determined."
     ::= { apEDCAStationEntry 5 }

apEDCAStationTxOpLimit OBJECT-TYPE 
     SYNTAX      INTEGER(0..65535)
     MAX-ACCESS  read-write
     STATUS      current
     DESCRIPTION
         "Specifies an interval of the time when a Wireless 
	  Multimedia Extensions(WME) client station has the right
          to initiate transmissions on to the wireless medium."
     ::= { apEDCAStationEntry 6 }

    
--*****************************************************************
--  apAssociation      OBJECT IDENTIFIER ::= { ciscosbWLANAP 7 }                            
--*****************************************************************

apAssocTable OBJECT-TYPE
    SYNTAX      SEQUENCE OF ApAssociationEntry
    MAX-ACCESS  not-accessible
    STATUS      current
    DESCRIPTION
            "A list of associated Clients on this AP."
    ::= { apAssociation 1 }

apAssociationEntry OBJECT-TYPE
    SYNTAX      ApAssociationEntry
    MAX-ACCESS  not-accessible
    STATUS      current
    DESCRIPTION
        "An entry containing the information applicable
        to an Associated Client."
    INDEX   { apAssocStationMac }
    ::= { apAssocTable 1 }

ApAssociationEntry ::=
    SEQUENCE {
        apAssocStationMac              MacAddress,
        apAssocInterface               DisplayString,
        apAssocAuthenticated           INTEGER,
        apAssocAssociated              INTEGER,
        apAssocRxPackets               Integer32,
        apAssocTxPackets               Integer32,
        apAssocRxBytes                 Integer32,
        apAssocTxBytes                 Integer32,
        apAssocListenInterval          Integer32,
        apAssocLastRssi                Integer32,
        apAssocTxDropBytes             Integer32,
        apAssocRxDropBytes             Integer32,
        apAssocTxDropPackets           Integer32,
        apAssocRxDropPackets           Integer32,
        apAssocClntQoSStatus	       DisplayString,
        apAssocBwLimitUp               Integer32,
        apAssocBwLimitDown             Integer32,
        apAssocACLTypeUp               DisplayString, 
        apAssocACLUp                   DisplayString,
        apAssocACLTypeDown             DisplayString,
        apAssocACLDown                 DisplayString,
        apAssocPolicyUp                DisplayString,
        apAssocPolicyDown              DisplayString,
        apAssocTsViolateTxPackets      Counter32,
        apAssocTsViolateRxPackets      Counter32,
        apAssocUptime           DisplayString
    }

apAssocStationMac OBJECT-TYPE
    SYNTAX      MacAddress
    MAX-ACCESS  not-accessible
    STATUS      current
    DESCRIPTION
            "MAC address of the station associated with this AP."
    ::= { apAssociationEntry 1 }

apAssocInterface   OBJECT-TYPE
    SYNTAX      DisplayString
    MAX-ACCESS  read-only
    STATUS      current
    DESCRIPTION
            "Radio Interface Name on which the client is associated."
    ::= { apAssociationEntry 2 }

apAssocAuthenticated OBJECT-TYPE
    SYNTAX	INTEGER {
                  yes(1),
                  no(2)
                }
    MAX-ACCESS  read-only
    STATUS      current
    DESCRIPTION
        "Indicates whether the Client is authenticated with the AP."
    ::= { apAssociationEntry 3 }

apAssocAssociated   OBJECT-TYPE
    SYNTAX	INTEGER {
                  yes(1),
                  no(2)
                }
    MAX-ACCESS  read-only
    STATUS      current
    DESCRIPTION
        "Indicates whether the Client is associated with the AP."
    ::= { apAssociationEntry 4 }

apAssocRxPackets OBJECT-TYPE
    SYNTAX     Integer32
    MAX-ACCESS  read-only
    STATUS      current
    DESCRIPTION
        "Count of packets received by this associated station."
    ::= { apAssociationEntry 5 }

apAssocTxPackets OBJECT-TYPE
    SYNTAX     Integer32
    MAX-ACCESS  read-only
    STATUS      current
    DESCRIPTION
        "Count of packets transmitted by this associated station."
    ::= { apAssociationEntry 6 }

apAssocRxBytes   OBJECT-TYPE
    SYNTAX     Integer32
    MAX-ACCESS  read-only
    STATUS      current
    DESCRIPTION
        "Count of bytes received by this associated station."
    ::= { apAssociationEntry 7 }

apAssocTxBytes OBJECT-TYPE
    SYNTAX     Integer32
    MAX-ACCESS  read-only
    STATUS      current
    DESCRIPTION
        "Count of bytes transmitted by this associated station."
    ::= { apAssociationEntry 8 }

apAssocListenInterval OBJECT-TYPE
    SYNTAX      Integer32
    MAX-ACCESS  read-only
    STATUS      current
    DESCRIPTION
            "Listen Interval."
    ::= { apAssociationEntry 9 }

apAssocLastRssi OBJECT-TYPE
    SYNTAX      Integer32
    MAX-ACCESS  read-only
    STATUS      current
    DESCRIPTION
            "Received Signal Strength Indicator of last frame."
    ::= { apAssociationEntry 10 }

apAssocTxDropBytes OBJECT-TYPE
    SYNTAX     Integer32
    MAX-ACCESS  read-only
    STATUS      current
    DESCRIPTION
        "Count of bytes transmitted by this associated station
        that were dropped."
    ::= { apAssociationEntry 11 }

apAssocRxDropBytes OBJECT-TYPE
    SYNTAX     Integer32
    MAX-ACCESS  read-only
    STATUS      current
    DESCRIPTION
        "Count of bytes received by this associated station
        that were dropped."
    ::= { apAssociationEntry 12 }

apAssocTxDropPackets OBJECT-TYPE
    SYNTAX     Integer32
    MAX-ACCESS  read-only
    STATUS      current
    DESCRIPTION
        "Count of packets transmitted by this associated station
        that were dropped."
    ::= { apAssociationEntry 13 }

apAssocRxDropPackets OBJECT-TYPE
    SYNTAX     Integer32
    MAX-ACCESS  read-only
    STATUS      current
    DESCRIPTION
        "Count of packets received by this associated station
        that were dropped."
    ::= { apAssociationEntry 14 }

apAssocClntQoSStatus OBJECT-TYPE
    SYNTAX     DisplayString
    MAX-ACCESS  read-only
    STATUS      current
    DESCRIPTION
        "Client QOS Status. Enabled if both, global QOS mode and
        QOS mode of the VAP, to which the client is associated
        are enabled."
    ::= { apAssociationEntry 15 }

apAssocBwLimitUp OBJECT-TYPE
    SYNTAX     Integer32 (1..4294967295)
    MAX-ACCESS  read-only
    STATUS      current
    DESCRIPTION
        "Maximum allowed transmission rate in bits per second (bps)
        to the client in client to AP direction."
    ::= { apAssociationEntry 16 }

apAssocBwLimitDown OBJECT-TYPE
    SYNTAX     Integer32 (1..4294967295)
    MAX-ACCESS  read-only
    STATUS      current
    DESCRIPTION
        "Maximum allowed transmission rate in bits per second (bps)
        to the client in AP to client direction."
    ::= { apAssociationEntry 17 }

apAssocACLTypeUp OBJECT-TYPE
    SYNTAX     DisplayString
    MAX-ACCESS  read-only
    STATUS      current
    DESCRIPTION
        "Type of acl applied to the selected client
        in client to AP direction."
    ::= { apAssociationEntry 18 }

apAssocACLUp OBJECT-TYPE
    SYNTAX     DisplayString
    MAX-ACCESS  read-only
    STATUS      current
    DESCRIPTION
        "Name of acl applied to the selected client
        in client to AP direction."
    ::= { apAssociationEntry 19 }

apAssocACLTypeDown OBJECT-TYPE
    SYNTAX     DisplayString
    MAX-ACCESS  read-only
    STATUS      current
    DESCRIPTION
        "Type of acl applied to the selected client
        in AP to client direction."
    ::= { apAssociationEntry 20 }

apAssocACLDown OBJECT-TYPE
    SYNTAX     DisplayString
    MAX-ACCESS  read-only
    STATUS      current
    DESCRIPTION
        "Name of acl applied to the selected client
        in AP to client direction."
    ::= { apAssociationEntry 21 }

apAssocPolicyUp OBJECT-TYPE
    SYNTAX     DisplayString
    MAX-ACCESS  read-only
    STATUS      current
    DESCRIPTION
        "Diffserv policy applied to the selected client
        in client to AP direction."
    ::= { apAssociationEntry 22 }

apAssocPolicyDown OBJECT-TYPE
    SYNTAX     DisplayString
    MAX-ACCESS  read-only
    STATUS      current
    DESCRIPTION
        "Diffserv policy applied to the selected client
        in AP to client direction."
    ::= { apAssociationEntry 23 }

--	 apAssocTsViolateTxPackets    Ts Violate Tx Packets

apAssocTsViolateTxPackets      OBJECT-TYPE
    SYNTAX     Counter32
    MAX-ACCESS  read-only
    STATUS      current
    DESCRIPTION
            "Count of TS violate packets transmitted by this associated Station."
    ::= { apAssociationEntry 24 }

--	 apAssocTsViolateRxPackets    Ts Violate Rx Packets

apAssocTsViolateRxPackets      OBJECT-TYPE
    SYNTAX     Counter32
    MAX-ACCESS  read-only
    STATUS      current
    DESCRIPTION
            "Count of TS violate packets received by this associated Station."
    ::= { apAssociationEntry 25 }

--	 apAssocAsssocDuration        Client association duration

apAssocUptime OBJECT-TYPE
    SYNTAX     DisplayString
    MAX-ACCESS  read-only
    STATUS      current
    DESCRIPTION
        "The time duration for which this station is associated with the AP."
    ::= { apAssociationEntry 26 }

-- apAssocTable ENDS

--**************************************************************************************
-- tspec (status and statistics) Begin
--**************************************************************************************

   apTspecClient                         OBJECT IDENTIFIER ::= { apTspecTables 6  }

--
--  apTspecClient
--
--
--   apAssocClientTspecStatusTable
--

 apAssocClientTspecStatusTable OBJECT-TYPE
     SYNTAX       SEQUENCE OF ApAssocClientTspecStatusEntry
     MAX-ACCESS   not-accessible
     STATUS       current
     DESCRIPTION
           "This table contains TSPEC traffic stream status parameters
            for clients currently associated with this AP.  Only
            clients possessing one or more active traffic streams 
            appear in this table."
     ::= { apTspecClient 1 }

    apAssocClientTspecStatusEntry OBJECT-TYPE
     SYNTAX       ApAssocClientTspecStatusEntry
     MAX-ACCESS   not-accessible
     STATUS       current
     DESCRIPTION
          "Each entry in this table contains TSPEC traffic stream status
           parameters for a specific client that is currently associated 
           with this AP."
     INDEX    { apAssocClientTspecStationMac, apAssocClientTspecTID }
     ::= { apAssocClientTspecStatusTable 1 }

  ApAssocClientTspecStatusEntry ::=
     SEQUENCE {
      apAssocClientTspecStationMac               MacAddress,
      apAssocClientTspecTID                      Unsigned32,
      apAssocClientTspecClientMac                MacAddress,
      apAssocClientTspecACIndex                  TspecSuppAC,
      apAssocClientTspecDirection                INTEGER,
      apAssocClientTspecUserPriority             Unsigned32,
      apAssocClientTspecMediumTime               Unsigned32,
      apAssocClientTspecExcessUsageEvents        Unsigned32,
      apAssocClientTspecInterface                DisplayString,
      apAssocClientTspecBSSID                    MacAddress,
      apAssocClientTspecSSID                     DisplayString
  }

 apAssocClientTspecStationMac OBJECT-TYPE
    SYNTAX      MacAddress
    MAX-ACCESS  not-accessible
    STATUS      current
    DESCRIPTION
            "MAC address of the station associated with this traffic stream."
    ::= { apAssocClientTspecStatusEntry 1 }

 apAssocClientTspecTID OBJECT-TYPE
     SYNTAX       Unsigned32(0..7)
     MAX-ACCESS   not-accessible
     STATUS       current
     DESCRIPTION
        "The traffic stream identifier (TID) indicated in the TSPEC that
         defines the traffic stream for the specified access category
         for the wireless client.  Each traffic stream for a particular
         client must have a unique TID in the range 0-7, but per specification,
         any TID may map to any user priority and hence to any access category.
         In this product, the only supported access categories are voice and 
         video.

         For a given access category, each wireless client can support one of
         the following:
           - one uplink traffic stream, or
           - one downlink traffic stream, or
           - one bidirectional traffic stream, or
           - one uplink and one downlink traffic stream simultaneously."
     ::= { apAssocClientTspecStatusEntry 2 }

 apAssocClientTspecClientMac OBJECT-TYPE
    SYNTAX      MacAddress
    MAX-ACCESS  read-only
    STATUS      current
    DESCRIPTION
            "MAC address of the client station associated with this traffic stream.
             This is the same as apAssocClientTspecStationMac but is 
             included in this row for display purposes."
    ::= { apAssocClientTspecStatusEntry 3 }

 apAssocClientTspecACIndex OBJECT-TYPE
      SYNTAX       TspecSuppAC
      MAX-ACCESS   read-only
      STATUS       current
      DESCRIPTION
            "TSPEC Access Category value (voice or video) for this client session."
      ::= { apAssocClientTspecStatusEntry 4 }

 apAssocClientTspecDirection OBJECT-TYPE
     SYNTAX       INTEGER {
                     uplink(1),
                     downlink(2), 
                     bidirectional(3)
                  }
     MAX-ACCESS   read-only
     STATUS       current
     DESCRIPTION
        "The direction of the client traffic stream (TS) as indicated
         in the TSPEC.  An uplink(1) TS monitors data traffic flowing
         from client station to AP, while a downlink(2) TS pertains to 
         the opposite direction.  A bidirectional(3) TS covers both
         directions and is treated as an uplink TS and downlink TS 
         operating concurrently for the specified access category."
     ::= { apAssocClientTspecStatusEntry 5 }

 apAssocClientTspecUserPriority  OBJECT-TYPE
     SYNTAX       Unsigned32
     MAX-ACCESS   read-only
     STATUS       current
     DESCRIPTION
        "The user priority indicated in the TSPEC that defines
         the traffic stream for the specified access category
         for the wireless client.  QoS Data frames to/from the client
         containing this user priority are categorized as belonging
         to the traffic stream, depending on direction."
     ::= { apAssocClientTspecStatusEntry 6 }

 apAssocClientTspecMediumTime OBJECT-TYPE
     SYNTAX       Unsigned32
     MAX-ACCESS   read-only
     STATUS       current
     DESCRIPTION
        "Indicates the amount of time this client is allowed to access
         the wireless medium each second for the specified access category through
         this traffic stream.  This value is calculated by the AP based
         on various parameters supplied in the TSPEC add request from 
         the client.
          
         The medium time is specified as the number of 32 microsecond time
         units the client is allowed to access the wireless network each
         second.  This is referred to as units of 32 usec-per-sec and is
         generally treated as an average value, with any over-usage
         in one interval deducted from the alotted medium time for the next
         interval."
     ::= { apAssocClientTspecStatusEntry 7 }

 apAssocClientTspecExcessUsageEvents OBJECT-TYPE
     SYNTAX       Unsigned32
     MAX-ACCESS   read-only
     STATUS       current
     DESCRIPTION
        "The number of times the wireless client has appreciably exceeded
         the medium time established for its TSPEC.  The actual measure    
         of 'appreciably exceeded' is implementation-dependent, but it is
         not necessarily a single occurrence of exceeding the medium time
         for any given one second interval.  Rather, this event may be
         indicated after repeated violations of the medium time over some 
         measurement interval, and is intended as an heuristic to identify
         a wireless client whose TSPEC medium time may be set too low relative
         to its actual traffic stream requirements."
     ::= { apAssocClientTspecStatusEntry 8 }

 apAssocClientTspecInterface   OBJECT-TYPE
     SYNTAX      DisplayString
     MAX-ACCESS  read-only
     STATUS      current
     DESCRIPTION
        "Radio interface name on which the client is associated."
     ::= { apAssocClientTspecStatusEntry 9 }

 apAssocClientTspecBSSID OBJECT-TYPE
    SYNTAX      MacAddress
    MAX-ACCESS  read-only
    STATUS      current
    DESCRIPTION
            "MAC address of the Virtual AP associated with this TSPEC."
    ::= { apAssocClientTspecStatusEntry 10 }

 apAssocClientTspecSSID OBJECT-TYPE
    SYNTAX      DisplayString
    MAX-ACCESS  read-only
    STATUS      current
    DESCRIPTION
            "SSID for the TSPEC client."
    ::= { apAssocClientTspecStatusEntry 11 }

--
--   apAssocClientTspecStatisticsTable
--

  apAssocClientTspecStatisticsTable OBJECT-TYPE
     SYNTAX       SEQUENCE OF ApAssocClientTspecStatisticsEntry
     MAX-ACCESS   not-accessible
     STATUS       current
     DESCRIPTION
           "This table contains TSPEC traffic stream statistics
            for clients currently associated with this AP.  Only
            clients possessing one or more active traffic streams 
            appear in this table."
     ::= { apTspecClient 2 }

  apAssocClientTspecStatisticsEntry OBJECT-TYPE
     SYNTAX       ApAssocClientTspecStatisticsEntry
     MAX-ACCESS   not-accessible
     STATUS       current
     DESCRIPTION
          "Each entry in this table contains TSPEC traffic stream statistics
           for a specific client that is currently associated with this
           AP."
     INDEX    { apAssocClientTspecStationMac, apAssocClientTspecTID }
     ::= { apAssocClientTspecStatisticsTable 1 }

  ApAssocClientTspecStatisticsEntry ::=
     SEQUENCE {
      apAssocClientTspecPktsRecvd            Counter64,
      apAssocClientTspecPktsTransmitted      Counter64,
      apAssocClientTspecBytesRecvd           Counter64,
      apAssocClientTspecBytesTransmitted     Counter64
 }

 apAssocClientTspecPktsRecvd OBJECT-TYPE
     SYNTAX       Counter64
     MAX-ACCESS   read-only
     STATUS       current
     DESCRIPTION
        "Total packets received from the client station for the 
         traffic stream belonging to the specified access category.
          
         This object is only valid when the apAssociatedClientTspecDirection
         is either uplink(1) or bidirectional(3)."
     ::= { apAssocClientTspecStatisticsEntry 1 }

 apAssocClientTspecPktsTransmitted OBJECT-TYPE
     SYNTAX       Counter64
     MAX-ACCESS   read-only
     STATUS       current
     DESCRIPTION
        "Total packets transmitted to the client station for the 
         traffic stream belonging to the specified access category.
          
         This object is only valid when the apAssociatedClientTspecDirection
         is either downlink(2) or bidirectional(3)."
     ::= { apAssocClientTspecStatisticsEntry 2 }

 apAssocClientTspecBytesRecvd OBJECT-TYPE
     SYNTAX       Counter64
     MAX-ACCESS   read-only
     STATUS       current
     DESCRIPTION
        "Total bytes received from the client station for the 
         traffic stream belonging to the specified access category.
          
         This object is only valid when the apAssociatedClientTspecDirection
         is either uplink(1) or bidirectional(3)."
     ::= { apAssocClientTspecStatisticsEntry 3 }

 apAssocClientTspecBytesTransmitted OBJECT-TYPE
     SYNTAX       Counter64
     MAX-ACCESS   read-only
     STATUS       current
     DESCRIPTION
        "Total bytes transmitted to the client station for the 
         traffic stream belonging to the specified access category.
          
         This object is only valid when the apAssociatedClientTspecDirection
         is either downlink(2) or bidirectional(3)."
     ::= { apAssocClientTspecStatisticsEntry 4 }

--**************************************************************************************
-- tspec (status and statistics) Ends
--**************************************************************************************

--*****************************************************************
-- apDetectedApTable   OBJECT IDENTIFIER ::= { ciscosbWLANAP 8 }
--*****************************************************************

apDetectedApTable OBJECT-TYPE
    SYNTAX      SEQUENCE OF ApDetectedApEntry
    MAX-ACCESS  not-accessible
    STATUS      current
    DESCRIPTION
            "A list of detected AP entries."
    ::= { apDetectedAp 1 }

apDetectedApEntry OBJECT-TYPE
    SYNTAX      ApDetectedApEntry
    MAX-ACCESS  not-accessible
    STATUS      current
    DESCRIPTION
            "An entry containing the information applicable 
	    to a detected Access Point."
    INDEX   { apDetectedApMac, apDetectedRadioName }
    ::= { apDetectedApTable 1 }

ApDetectedApEntry ::=
    SEQUENCE {
        apDetectedApMac              MacAddress,
	apDetectedRadioName          OCTET STRING,
        apDetectedApBeaconInterval   Integer32,
        apDetectedApCapability       DisplayString,
        apDetectedApType             DisplayString,
        apDetectedApPrivacy          INTEGER,
        apDetectedApSsid             DisplayString,
        apDetectedApWpa              INTEGER,
        apDetectedApPhyType	     INTEGER,
        apDetectedApBand	     DisplayString,
        apDetectedApChannel	     Integer32,
        apDetectedApRate	     Integer32,
        apDetectedApSignal	     Integer32,
        apDetectedApErp              DisplayString,
        apDetectedApBeacons          Integer32,
        apDetectedApLastBeacon       DisplayString,
        apDetectedApSupportedRates   DisplayString
    }

apDetectedApMac OBJECT-TYPE
        SYNTAX      MacAddress
        MAX-ACCESS  not-accessible
        STATUS      current
        DESCRIPTION
            "MAC address of the detected neighbor APs."
        ::= { apDetectedApEntry 1 }

apDetectedRadioName       OBJECT-TYPE
     SYNTAX      OCTET STRING (SIZE(0..32)) 
     MAX-ACCESS  not-accessible
     STATUS      current
     DESCRIPTION
         "Radio used to scan the detected SSID."
     ::= { apDetectedApEntry 2 }

apDetectedApBeaconInterval OBJECT-TYPE
    SYNTAX	Integer32 
    MAX-ACCESS  read-only
    STATUS      current
    DESCRIPTION
        "Beacon Interval for the detected AP in terms of TU.
        TU is measurement of time equal to 1024 micro seconds."
    ::= { apDetectedApEntry 3 }

apDetectedApCapability OBJECT-TYPE
    SYNTAX      DisplayString
    MAX-ACCESS  read-only
    STATUS      current
    DESCRIPTION
        "The capability of the detected AP, represented as a
        hexadecimal bitflag. The bit definitions are:
             0x0001 - AP
             0x0002 - Ad-Hoc
             0x0010 - Privacy
             0x0020 - Short preamble
             0x0100 - Spectrum management
             0x0400 - Short slot"
    ::= { apDetectedApEntry 4 }

apDetectedApType OBJECT-TYPE
    SYNTAX      DisplayString
    MAX-ACCESS  read-only
    STATUS      current
    DESCRIPTION
            "The type of device detected.
             Values can be AP, Ad hoc, or Other."
    ::= { apDetectedApEntry 5 }

apDetectedApPrivacy OBJECT-TYPE
    SYNTAX     INTEGER { 
                on(1),
                off(2)
               }
    MAX-ACCESS  read-only
    STATUS      current
    DESCRIPTION
        "Indicates whether privacy (WEP or WPA) is enabled."
    ::= { apDetectedApEntry 6 }

apDetectedApSsid OBJECT-TYPE
    SYNTAX      DisplayString 
    MAX-ACCESS  read-only
    STATUS      current
    DESCRIPTION
            "SSID of the AP."
    ::= { apDetectedApEntry 7 }

apDetectedApWpa OBJECT-TYPE
    SYNTAX     INTEGER { 
                on(1),
                off(2)
               }
    MAX-ACCESS  read-only
    STATUS      current
    DESCRIPTION
            "Whether WPA is enabled on the scanned SSID."
    ::= { apDetectedApEntry 8 }

apDetectedApPhyType OBJECT-TYPE
    SYNTAX      INTEGER {
                invalid(0),
                fhssdot1197(1),
                dsssdot1197(2),
                irbaseband(3),
                dsssdot11b(4),
                pbccdot11b(5),
                ofdmdot11g(6),
                pbccdot11g(7),
                ofdmdot11a(8),
                dsssdot11turbog(255),
                dsssdot11turbo(256)
                }        
    MAX-ACCESS  read-only
    STATUS      current
    DESCRIPTION
            "Mode the radio was in when the AP was detected. 
         Note that in B or G mode, it is possible to detect both
         B and G APs, therefore the distinction between B and G
         is not useful information."
    ::= { apDetectedApEntry 9 }

apDetectedApBand OBJECT-TYPE
    SYNTAX      DisplayString
    MAX-ACCESS  read-only
    STATUS      current
    DESCRIPTION
            "The RF band the AP was detected in.
             Values can be 2.4, 5, or 5 Turbo."
    ::= { apDetectedApEntry 10 }

apDetectedApChannel OBJECT-TYPE
    SYNTAX      Integer32
    MAX-ACCESS  read-only
    STATUS      current
    DESCRIPTION
            "Channel on which the AP is detected." 
    ::= { apDetectedApEntry 11 }

apDetectedApRate OBJECT-TYPE
    SYNTAX      Integer32
    MAX-ACCESS  read-only
    STATUS      current
    DESCRIPTION
            "The basic rate at which the AP sends beacons."
    ::= { apDetectedApEntry 12 }

apDetectedApSignal OBJECT-TYPE
    SYNTAX      Integer32
    MAX-ACCESS  read-only
    STATUS      current
    DESCRIPTION
            "Signal Strength of the AP."
    ::= { apDetectedApEntry 13 }

apDetectedApErp OBJECT-TYPE
    SYNTAX      DisplayString
    MAX-ACCESS  read-only
    STATUS      current
    DESCRIPTION
        "The Extended PHY Rate (ERP) of the detected AP, represented
        as a hexadecimal number. The bit definitions are:

                 0x01 - Non ERP (802.11b) STAs are present in the BSS
                 0x02 - Use protection mechanisms for ERP-OFDM frames
                 0x04 - Short preambles: 0 - allowed, 1 - not allowed
        A hyphen (-) indicates no ERP info (i.e. not in 2.4 GHz band)"
    ::= { apDetectedApEntry 14 }

apDetectedApBeacons OBJECT-TYPE
    SYNTAX      Integer32
    MAX-ACCESS  read-only
    STATUS      current
    DESCRIPTION
            "Counter of Beacons received from this AP."
    ::= { apDetectedApEntry 15 }

apDetectedApLastBeacon OBJECT-TYPE
    SYNTAX      DisplayString
    MAX-ACCESS  read-only
    STATUS      current
    DESCRIPTION
            "Time of last beacon received."
    ::= { apDetectedApEntry 16 }

apDetectedApSupportedRates OBJECT-TYPE
    SYNTAX      DisplayString
    MAX-ACCESS  read-only
    STATUS      current
    DESCRIPTION
            "Supported rates of the detected AP."
    ::= { apDetectedApEntry 17 }

--*****************************************************************
--  apDetectedRogueApTrap         OBJECT IDENTIFIER ::= { apDetectedAp 2 }
--*****************************************************************

apDetectedRogueApTrapPrefix       OBJECT IDENTIFIER
                ::= { apDetectedRogueApTrap 0 }

apDetectedRogueApTrapObjects      OBJECT IDENTIFIER
                ::= { apDetectedRogueApTrap 1 }

apDetectedRogueApTrapSeverity     OBJECT-TYPE
SYNTAX          SnmpAdminString
MAX-ACCESS      accessible-for-notify
STATUS          current
DESCRIPTION     "This string contains the severity of trap message."
::= {apDetectedRogueApTrapObjects 1 }

apDetectedRogueApTrapTrapMessage      OBJECT-TYPE
SYNTAX          SnmpAdminString
MAX-ACCESS      accessible-for-notify
STATUS          current
DESCRIPTION     "This string contains the contents of trap message."
::= { apDetectedRogueApTrapObjects        2 }

apDetectedRogueApTrapMacAddress   OBJECT-TYPE
SYNTAX          SnmpAdminString
MAX-ACCESS      accessible-for-notify
STATUS          current
DESCRIPTION     "This string contains the AP MAC address."
::= { apDetectedRogueApTrapObjects        3 }

apDetectedRogueApTrapSsid       OBJECT-TYPE
SYNTAX          SnmpAdminString
MAX-ACCESS      accessible-for-notify
STATUS          current
DESCRIPTION     "This string contains the SSID."
::= { apDetectedRogueApTrapObjects        4}

apDetectedRogueApTrapChannal       OBJECT-TYPE
SYNTAX          SnmpAdminString
MAX-ACCESS      accessible-for-notify
STATUS          current
DESCRIPTION     "This string contains the Channel."
::= { apDetectedRogueApTrapObjects        5}

apDetectedRogueApTrapNotification  NOTIFICATION-TYPE
            OBJECTS {
                        apDetectedRogueApTrapSeverity,
                        apDetectedRogueApTrapTrapMessage,
                        apDetectedRogueApTrapMacAddress,
                        apDetectedRogueApTrapSsid,
                        apDetectedRogueApTrapChannal
                    }
            STATUS  current
            DESCRIPTION
                  "Object which contains information about the Detected Rogue AP."
            ::= { apDetectedRogueApTrapPrefix 1}


--*****************************************************************
--      apRadioRates      OBJECT IDENTIFIER ::= { ciscosbWLANAP 9 }
--*****************************************************************

apRadioBasicRateTable OBJECT-TYPE
    SYNTAX      SEQUENCE OF ApRadioBasicRateEntry
    MAX-ACCESS  not-accessible
    STATUS      current
    DESCRIPTION
            "A list of basic rates."
    ::= { apRadioRates 1 }

apRadioBasicRateEntry OBJECT-TYPE
    SYNTAX      ApRadioBasicRateEntry
    MAX-ACCESS  not-accessible
    STATUS      current
    DESCRIPTION
            "An entry containing information applicable to 
             basic rates of a particular radio."
    INDEX   { apBasicRateRadioName, apRadioBasicRate}
    ::= { apRadioBasicRateTable 1 }

ApRadioBasicRateEntry ::=
    SEQUENCE {
	apBasicRateRadioName	    OCTET STRING,
	apRadioBasicRate	    OCTET STRING,
        apRadioBasicRateStatus      RowStatus
    }

apBasicRateRadioName OBJECT-TYPE
    SYNTAX      OCTET STRING (SIZE(0..32))
    MAX-ACCESS  not-accessible
    STATUS      current
    DESCRIPTION
            "AP radio to which the basic rate applies."
    ::= { apRadioBasicRateEntry 1 }

apRadioBasicRate       OBJECT-TYPE
        SYNTAX          OCTET STRING (SIZE(0..32))
        MAX-ACCESS      not-accessible
        STATUS          current
        DESCRIPTION             
                "Basic rate value."
        ::= { apRadioBasicRateEntry 2 }

apRadioBasicRateStatus  OBJECT-TYPE
        SYNTAX          RowStatus
        MAX-ACCESS      read-create
        STATUS          current
        DESCRIPTION             
                "Status of an entry. Supported values are:
                 - active (1)
                 - createAndGo (4)
                 - createAndWait (5)
                 - destroy (6)

        The administrator can only use createAndGo, createAndWait,
        and destroy. After creating an entry, its status is moved
        to active."
        ::= { apRadioBasicRateEntry 3 }


--*****************************************************************
-- apRadioSuppRateTable
--*****************************************************************

apRadioSuppRateTable OBJECT-TYPE
    SYNTAX      SEQUENCE OF ApRadioSuppRateEntry
    MAX-ACCESS  not-accessible
    STATUS      current
    DESCRIPTION
            "A list of radio supported rates."
    ::= { apRadioRates 2 }

apRadioSuppRateEntry OBJECT-TYPE
    SYNTAX      ApRadioSuppRateEntry
    MAX-ACCESS  not-accessible
    STATUS      current
    DESCRIPTION
     "An entry containing information applicable to supported rates 
             of a particular radio."
    INDEX   { apSuppRateRadioName, apRadioSuppRate }
    ::= { apRadioSuppRateTable 1 }

ApRadioSuppRateEntry ::=
    SEQUENCE {
	apSuppRateRadioName	   OCTET STRING,
	apRadioSuppRate            OCTET STRING,
        apRadioSuppRateStatus      RowStatus
    }

apSuppRateRadioName OBJECT-TYPE
    SYNTAX      OCTET STRING (SIZE(0..32))
    MAX-ACCESS  not-accessible
    STATUS      current
    DESCRIPTION
            "AP radio to which the supported rate applies."
    ::= { apRadioSuppRateEntry 1 }

apRadioSuppRate       OBJECT-TYPE
        SYNTAX          OCTET STRING (SIZE(0..32))
        MAX-ACCESS      not-accessible
        STATUS          current
        DESCRIPTION             
                "Supported rate value."
        ::= { apRadioSuppRateEntry 2 }

apRadioSuppRateStatus  OBJECT-TYPE
        SYNTAX          RowStatus
        MAX-ACCESS      read-create
        STATUS          current
        DESCRIPTION             
                "Status of an entry. Supported values are:
                 - active (1)
                 - createAndGo (4)
                 - createAndWait (5)
                 - destroy (6)

         The administrator can only use createAndGo, createAndWait,
         and destroy. After creating an entry, its status is moved
         to active."
        ::= { apRadioSuppRateEntry 3 }


--*****************************************************************
-- apRadioMcsIndexTable
--*****************************************************************

apRadioMcsIndexTable OBJECT-TYPE
    SYNTAX      SEQUENCE OF ApRadioMcsIndexEntry
    MAX-ACCESS  not-accessible
    STATUS      current
    DESCRIPTION
            "A list of radio supported MCS Indicies."
    ::= { apRadioRates 3 }

apRadioMcsIndexEntry OBJECT-TYPE
    SYNTAX      ApRadioMcsIndexEntry
    MAX-ACCESS  not-accessible
    STATUS      current
    DESCRIPTION
     "An entry containing information applicable to MCS Index 
             of a particular radio."
    INDEX   { apMcsIndexRadioName, apRadioMcsIndex }
    ::= { apRadioMcsIndexTable 1 }

ApRadioMcsIndexEntry ::=
    SEQUENCE {
	apMcsIndexRadioName	   OCTET STRING,
	apRadioMcsIndex            Integer32,
        apRadioMcsIndexStatus      RowStatus
    }

apMcsIndexRadioName OBJECT-TYPE
    SYNTAX      OCTET STRING (SIZE(0..32))
    MAX-ACCESS  not-accessible
    STATUS      current
    DESCRIPTION
            "AP radio to which the MCS Index applies."
    ::= { apRadioMcsIndexEntry 1 }

apRadioMcsIndex       OBJECT-TYPE
        SYNTAX          Integer32
        MAX-ACCESS      not-accessible
        STATUS          current
        DESCRIPTION             
                "Supported index."
        ::= { apRadioMcsIndexEntry 2 }

apRadioMcsIndexStatus  OBJECT-TYPE
        SYNTAX          RowStatus
        MAX-ACCESS      read-create
        STATUS          current
        DESCRIPTION             
                "Status of an entry. Supported values are:
                 - active (1)
                 - createAndGo (4)
                 - createAndWait (5)
                 - destroy (6)

         The administrator can only use createAndGo, createAndWait,
         and destroy. After creating an entry, its status is moved
         to active."
        ::= { apRadioMcsIndexEntry 3 }


--*****************************************************************
--      apQosGlobalMode    OBJECT IDENTIFIER ::= { apQos 1 }
--*****************************************************************

    apQosGlobalMode OBJECT-TYPE
         SYNTAX      INTEGER {
                      up(1),
                      down(2)
                }
         MAX-ACCESS  read-write
         STATUS      current
         DESCRIPTION
                     "Configure Client QoS Global Admin Mode."
         ::= { apQos 1 }

--*****************************************************************
-- apQosAclTable
--*****************************************************************

    apQosAclTable OBJECT-TYPE
         SYNTAX      SEQUENCE OF ApQosAclEntry
         MAX-ACCESS  not-accessible
         STATUS      current
         DESCRIPTION
                     "A table of ACL instances."
         ::= { apQos 2 }

    apQosAclEntry OBJECT-TYPE
         SYNTAX      ApQosAclEntry
         MAX-ACCESS  not-accessible
         STATUS      current
         DESCRIPTION
        "An ACL instance entry."
         INDEX       { apQosAclType, apQosAclName }
         ::= { apQosAclTable 1 }

ApQosAclEntry ::=
    SEQUENCE {
        apQosAclType            INTEGER,
        apQosAclName            DisplayString,
        apQosAclStatus          RowStatus
       }

    apQosAclType OBJECT-TYPE
         SYNTAX      INTEGER {
                      ipv4(1),
                ipv6(2)
                }
         MAX-ACCESS  not-accessible
         STATUS      current
         DESCRIPTION
                     "The type of this IP ACL entry."
         ::= { apQosAclEntry 1 }

    apQosAclName OBJECT-TYPE
         SYNTAX      DisplayString (SIZE(1..31))
         MAX-ACCESS  not-accessible
         STATUS      current
         DESCRIPTION
        "The name of this IP ACL entry, which must consist of 1 to 31
        alphanumeric characters and uniquely identify this IP ACL."
         ::= { apQosAclEntry 2 }

    apQosAclStatus OBJECT-TYPE
         SYNTAX      RowStatus
         MAX-ACCESS  read-create
         STATUS      current
         DESCRIPTION
                "Status of an entry. Supported values are:
                 - active (1)
                 - createAndGo (4)
                 - destroy (6)

        The administrator can only use createAndGo
        and destroy. After creating an entry, its status is moved
        to active."
         ::= { apQosAclEntry 3 }


--*****************************************************************
--      apQosAclRuleTable OBJECT IDENTIFIER ::= { apQos 3 }
--*****************************************************************

    apQosAclRuleTable OBJECT-TYPE
         SYNTAX      SEQUENCE OF ApQosAclRuleEntry
         MAX-ACCESS  not-accessible
         STATUS      current
         DESCRIPTION
                     "A table of IP ACL Rule instances."
         ::= { apQos 3 }

    apQosAclRuleEntry OBJECT-TYPE
         SYNTAX      ApQosAclRuleEntry
         MAX-ACCESS  not-accessible
         STATUS      current
         DESCRIPTION
        "An IP ACL Rule instance entry."
         INDEX       { apQosAclType, apQosAclName, apQosAclRuleIndex }
         ::= { apQosAclRuleTable 1 }

ApQosAclRuleEntry ::=
    SEQUENCE {
        apQosAclRuleIndex               Integer32,
        apQosAclRuleAction              INTEGER,
        apQosAclRuleProtocol            Integer32,
        apQosAclRuleSrcIpAddress        InetAddress,
        apQosAclRuleSrcIpMask           InetAddress,
        apQosAclRuleSrcL4Port           Integer32,
        apQosAclRuleDstIpAddress        InetAddress,
        apQosAclRuleDstIpMask           InetAddress,
        apQosAclRuleDstL4Port           Integer32,
        apQosAclRuleIpTosBits           OCTET STRING,
        apQosAclRuleIpTosMask           OCTET STRING,
        apQosAclRuleIpDscp              Integer32,
        apQosAclRuleIpPrecedence        Integer32,
        apQosAclRuleStatus              RowStatus,
        apQosAclRuleMatchEvery          TruthValue,
        apQosAclRuleCommit              Integer32,
        apQosAclRuleSrcIpv6Address      InetAddress,
        apQosAclRuleSrcIpv6Prefix       Integer32,
        apQosAclRuleDstIpv6Address      InetAddress,
        apQosAclRuleDstIpv6Prefix       Integer32,
        apQosAclRuleIpv6FlowLabel       DisplayString 
        }

    apQosAclRuleIndex OBJECT-TYPE
         SYNTAX      Integer32
         MAX-ACCESS  not-accessible
         STATUS      current
         DESCRIPTION
                     "The index of this rule instance within an IP ACL."
         ::= { apQosAclRuleEntry 1 }

    apQosAclRuleAction OBJECT-TYPE
         SYNTAX      INTEGER {
                      permit(1),
                      deny(2)
                      }
         MAX-ACCESS  read-create
         STATUS      current
         DESCRIPTION
                     "The type of action this rule should perform."
         DEFVAL { deny }
         ::= { apQosAclRuleEntry 2 }

    apQosAclRuleProtocol OBJECT-TYPE
         SYNTAX      Integer32 (1..255)
         MAX-ACCESS  read-create
         STATUS      current
         DESCRIPTION
                     "icmp - 1
                      igmp - 2
                      ip - 4
                      tcp - 6
                      udp - 17
                      All values from 1 to 255 are valid."
         ::= { apQosAclRuleEntry 3 }

    apQosAclRuleSrcIpAddress OBJECT-TYPE
         SYNTAX      InetAddress
         MAX-ACCESS  read-create
         STATUS      current
         DESCRIPTION
      "The Source IPV4 Address used in the ACL Classification."
         ::= { apQosAclRuleEntry 4 }

    apQosAclRuleSrcIpMask OBJECT-TYPE
         SYNTAX      InetAddress
         MAX-ACCESS  read-create
         STATUS      current
         DESCRIPTION
        "The Source IPV4 Mask used in the ACL Classification.
         This mask is expressed using wild-card notation, which
         is the ones' complement of traditional Subnet Masks.
         Here, the 'Don't care bits' are represented by binary 1's and
        'Do care bits' are represented by binary 0's. For example,
        an 8-bit network mask is specified for this object as
        0.255.255.255 while a 24-bit network mask is 0.0.0.255."
         ::= { apQosAclRuleEntry 5 }

    apQosAclRuleSrcL4Port OBJECT-TYPE
         SYNTAX      Integer32
         MAX-ACCESS  read-create
         STATUS      current
         DESCRIPTION
        "The Source Port (Layer 4) used in ACL classification.
        The following are defined:
         ftpdata-20, ftp-21, telnet-23, smtp-25, tftp-69, 
         http/www-80, snmp-161.All values from 0-65535 are valid."
         ::= { apQosAclRuleEntry 6 }

    apQosAclRuleDstIpAddress OBJECT-TYPE
         SYNTAX      InetAddress
         MAX-ACCESS  read-create
         STATUS      current
         DESCRIPTION
        "The Destination IPV4 Address used in the ACL Classification."
         ::= { apQosAclRuleEntry 7 }

    apQosAclRuleDstIpMask OBJECT-TYPE
         SYNTAX      InetAddress
         MAX-ACCESS  read-create
         STATUS      current
         DESCRIPTION
        "The Destination  IPV4 Mask used in the ACL Classification.
         This mask is expressed using wild-card notation, which
         is the ones' complement of traditional Subnet Masks.
         Here, the 'Don't care bits' are represented by binary 1's and
        'Do care bits' are represented by binary 0's. For example,
        an 8-bit network mask is specified for this object as
        0.255.255.255 while a 24-bit network mask is 0.0.0.255."
         ::= { apQosAclRuleEntry 8 }

    apQosAclRuleDstL4Port OBJECT-TYPE
         SYNTAX      Integer32
         MAX-ACCESS  read-create
         STATUS      current
         DESCRIPTION
        "The Destination Port (Layer 4) used in ACL classification.
        The following are defined:
         ftpdata-20, ftp-21, telnet-23, smtp-25, domain-53, tftp-69, 
        http/www-80, snmp-161.All values from 0-65535 are valid."
         ::= { apQosAclRuleEntry 9 }

    apQosAclRuleIpTosBits OBJECT-TYPE
         SYNTAX      OCTET STRING
         MAX-ACCESS  read-create
         STATUS      current
         DESCRIPTION
        "The Type of Service (TOS) Bits value. By definition, 
         the high-order three bits represent the IP precedence value, 
         whereas alternatively the high-order six bits represent the IP 
        Differentiated Services Code Point (DSCP) value.Valid values are 0x00-0xFF."
         ::= { apQosAclRuleEntry 10 }

    apQosAclRuleIpTosMask OBJECT-TYPE
         SYNTAX      OCTET STRING
         MAX-ACCESS  read-create
         STATUS      current
         DESCRIPTION
        "The Type of Service (TOS) Mask value. By definition, 
         the high-order three bits represent the IP precedence value, 
         whereas alternatively the high-order six bits represent the IP 
        Differentiated Services Code Point (DSCP) value.  Therefore,
        a mask of 0xE0 is used for IP precedence, while mask of 0xFC
        is used for IP DSCP.Valid values are 0x00-0xFF."
         ::= { apQosAclRuleEntry 11 }

    apQosAclRuleIpDscp OBJECT-TYPE
         SYNTAX      Integer32 (0..63)
         MAX-ACCESS  read-create
         STATUS      current
         DESCRIPTION
       "IP DiffServ Code Point (DSCP) match value for the ACL rule.  
        The DSCP is defined as the high-order six bits of the
        Service Type octet in the IPv4 header."
         ::= { apQosAclRuleEntry 12 }

    apQosAclRuleIpPrecedence OBJECT-TYPE
         SYNTAX      Integer32 (0..7)
         MAX-ACCESS  read-create
         STATUS      current
         DESCRIPTION
                     "IP Precedence match value for the ACL rule.
        The Precedence bits are defined as the high-order three bits
        of the Service Type octed in the IPv4 header."
         ::= { apQosAclRuleEntry 13 }

    apQosAclRuleStatus OBJECT-TYPE
         SYNTAX      RowStatus
         MAX-ACCESS  read-create
         STATUS      current
         DESCRIPTION
                "Status of an entry. Supported values are:
                 - active (1)
                 - createAndGo (4)

       The administrator can only use createAndGo and createAndWait. 
        After creating an entry, its status is moved to active."
         ::= { apQosAclRuleEntry 14 }

    apQosAclRuleMatchEvery OBJECT-TYPE
         SYNTAX      TruthValue
         MAX-ACCESS  read-create
         STATUS      current
         DESCRIPTION
        "Flag to indicate that the ACL rule is defined to match on
        every IP packet, regardless of content. If set to true(1), all
        other classification field objects in this row are ignored.
        Error is returned for all other values set."
         DEFVAL { false }
         ::= { apQosAclRuleEntry 15 }

    apQosAclRuleCommit OBJECT-TYPE
         SYNTAX      Integer32 
         MAX-ACCESS  read-create
         STATUS      current
         DESCRIPTION
       "Flag to indicate that to apply all the rule attributes 
        created for this row entry. This can be set only once.
        Once committed, the rule properties cannot be changed.The
        commit value after successful commit is 3."
         ::= { apQosAclRuleEntry 16 }

    apQosAclRuleSrcIpv6Address OBJECT-TYPE
         SYNTAX      InetAddress
         MAX-ACCESS  read-create
         STATUS      current
         DESCRIPTION
        "The Source IPV6 Address used in the ACL Classification."
         ::= { apQosAclRuleEntry 17 }

    apQosAclRuleSrcIpv6Prefix OBJECT-TYPE
         SYNTAX      Integer32 (0..128)
         MAX-ACCESS  read-create
         STATUS      current
         DESCRIPTION
       	"Source IPv6 Prefix Len."
         ::= { apQosAclRuleEntry 18 }

   apQosAclRuleDstIpv6Address OBJECT-TYPE
         SYNTAX      InetAddress
         MAX-ACCESS  read-create
         STATUS      current
         DESCRIPTION
      "The Destination IPV6 Address used in the ACL Classification."
         ::= { apQosAclRuleEntry 19 }

    apQosAclRuleDstIpv6Prefix OBJECT-TYPE
         SYNTAX      Integer32 (0..128)
         MAX-ACCESS  read-create
         STATUS      current
         DESCRIPTION
      	"Destination IPv6 Prefix Len."
         ::= { apQosAclRuleEntry 20 }

    apQosAclRuleIpv6FlowLabel OBJECT-TYPE
         SYNTAX      DisplayString
         MAX-ACCESS  read-create
         STATUS      current
         DESCRIPTION
      "The IPv6 Flow Label match value for the class. Hex values in
         the range of 00000 - FFFFF."
         ::= { apQosAclRuleEntry 21 }


--*****************************************************************
--      apQosDsClassMapTable    OBJECT IDENTIFIER ::= { apQos 4 }
--*****************************************************************

    apQosDsClassMapTable OBJECT-TYPE
         SYNTAX      SEQUENCE OF ApQosDsClassMapEntry
         MAX-ACCESS  not-accessible
         STATUS      current
         DESCRIPTION
                     "A table of class-map instances."
         ::= { apQos 4 }

    apQosDsClassMapEntry OBJECT-TYPE
         SYNTAX      ApQosDsClassMapEntry
         MAX-ACCESS  not-accessible
         STATUS      current
         DESCRIPTION
        "A class-map instance entry."
         INDEX       {apQosDsClassMapMatchL3Protocol,apQosDsClassMapName}
         ::= { apQosDsClassMapTable 1 }

ApQosDsClassMapEntry ::=
    SEQUENCE {
        apQosDsClassMapName                     DisplayString,
        apQosDsClassMapMatchL3Protocol          INTEGER,
        apQosDsClassMapStatus                   RowStatus,
        apQosDsClassMapMatchEvery               TruthValue,
        apQosDsClassMapMatchDstMac              MacAddress,
        apQosDsClassMapMatchDstMacMask          MacAddress,
        apQosDsClassMapMatchDstIpAddress        InetAddress,
        apQosDsClassMapMatchDstIpMask           InetAddress,
        apQosDsClassMapMatchDstL4Port           Integer32,
        apQosDsClassMapMatchCos                 Integer32,
        apQosDsClassMapMatchEthertype           DisplayString,
        apQosDsClassMapMatchIpTosBits           OCTET STRING,
        apQosDsClassMapMatchIpTosMask           OCTET STRING,
        apQosDsClassMapMatchIpDscp              Integer32,
        apQosDsClassMapMatchIpPrecedence        Integer32,
        apQosDsClassMapMatchProtocol            Integer32,
        apQosDsClassMapMatchSrcMac              MacAddress,
        apQosDsClassMapMatchSrcMacMask          MacAddress,
        apQosDsClassMapMatchSrcIpAddress        InetAddress,
        apQosDsClassMapMatchSrcIpMask           InetAddress,
        apQosDsClassMapMatchSrcL4Port           Integer32,
        apQosDsClassMapMatchVlanId              Integer32,
        apQosDsClassMapMatchCommit              Integer32,
        apQosDsClassMapMatchFlags               Integer32,
        apQosDsClassMapMatchSrcIpv6Address      InetAddress,
        apQosDsClassMapMatchSrcIpv6Prefix       Integer32,
        apQosDsClassMapMatchDstIpv6Address      InetAddress,
        apQosDsClassMapMatchDstIpv6Prefix       Integer32,
        apQosDsClassMapMatchIpv6FlowLabel       DisplayString
        }

    apQosDsClassMapName OBJECT-TYPE
         SYNTAX      DisplayString (SIZE(1..31))
         MAX-ACCESS  not-accessible
         STATUS      current
         DESCRIPTION
        "Name of this class-map entry, which must consist of 1 to 31
        alphanumeric characters and uniquely identify this class-map."
         ::= { apQosDsClassMapEntry 1 }

    apQosDsClassMapMatchL3Protocol OBJECT-TYPE
         SYNTAX      INTEGER {
                      ipv4(1),
                ipv6(2)
                }
         MAX-ACCESS  not-accessible
         STATUS      current
         DESCRIPTION
        "The Layer3 protocol match value used for the class.
        This will be the type of this class-map."
         ::= { apQosDsClassMapEntry 2 }

    apQosDsClassMapStatus OBJECT-TYPE
         SYNTAX      RowStatus
         MAX-ACCESS  read-create
         STATUS      current
         DESCRIPTION
                "Status of an entry. Supported values are:
                 - active (1)
                 - createAndGo (4)
                 - destroy (6)

        The administrator can only use createAndGo, createAndWait,
        and destroy. After creating an entry, its status is moved
        to active."
         ::= { apQosDsClassMapEntry 3 }

    apQosDsClassMapMatchEvery OBJECT-TYPE
         SYNTAX      TruthValue
         MAX-ACCESS  read-create
         STATUS      current
         DESCRIPTION
        "Flag to indicate that match attribute is defined to match on
        every IP packet, regardless of content. If set to true(1), all
        other classification field objects in this row are ignored.
        Error is returned for all other values set."    
         DEFVAL { false }
         ::= { apQosDsClassMapEntry 4 }

    apQosDsClassMapMatchDstMac OBJECT-TYPE
         SYNTAX      MacAddress
         MAX-ACCESS  read-create
         STATUS      current
         DESCRIPTION
        "Destination MAC address match value for the class."
         ::= { apQosDsClassMapEntry 5 }

    apQosDsClassMapMatchDstMacMask OBJECT-TYPE
         SYNTAX      MacAddress
         MAX-ACCESS  read-create
         STATUS      current
         DESCRIPTION
        "Destination MAC address mask match value for the class."
         ::= { apQosDsClassMapEntry 6 }

    apQosDsClassMapMatchDstIpAddress OBJECT-TYPE
         SYNTAX      InetAddress
         MAX-ACCESS  read-create
         STATUS      current
         DESCRIPTION
       "The Destination IP Address match value for the class."
         ::= { apQosDsClassMapEntry 7 }

    apQosDsClassMapMatchDstIpMask OBJECT-TYPE
         SYNTAX      InetAddress
         MAX-ACCESS  read-create
         STATUS      current
         DESCRIPTION
       "Destination IP address mask match value for the class. 
        This mask value identifies the portion of
        apQosDsClassMapMatchDstIpAddress that is compared against
        a packet."
         ::= { apQosDsClassMapEntry 8 }

    apQosDsClassMapMatchDstL4Port OBJECT-TYPE
         SYNTAX      Integer32
         MAX-ACCESS  read-create
         STATUS      current
         DESCRIPTION
        "Destination Port (Layer 4) used in class-map classification.
        Different port numbers are:
         ftpdata-20, ftp-21, telnet-23, smtp-25, domain-53, tftp-69, 
        http/www-80, snmp-161.All values from 0-65535 are valid."
         ::= { apQosDsClassMapEntry 9 }

    apQosDsClassMapMatchCos OBJECT-TYPE
         SYNTAX      Integer32 (0..7)
         MAX-ACCESS  read-create
         STATUS      current
         DESCRIPTION
       "Three-bit user priority field in the 802.1Q tag header 
         of a tagged Ethernet frame used as a class-match parameter."
         ::= { apQosDsClassMapEntry 10 }

    apQosDsClassMapMatchEthertype OBJECT-TYPE
         SYNTAX      DisplayString
         MAX-ACCESS  read-create
         STATUS      current
         DESCRIPTION
        "The Ethertype match value for the class. Hex values in the
         range of 0x0600-0xFFFF. Different ethertype key values are
         appletalk(0x02), arp(0x03), ibmsna(0x04), ipv4(0x05), ipv6(0x06),
         ipx(0x07), mplsmcast(0x08), mplsucast(0x09), netbios(0x0a), novell(0x0b),
         pppoe(0x0c), rarp(0x0d)."
         ::= { apQosDsClassMapEntry 11 }

    apQosDsClassMapMatchIpTosBits OBJECT-TYPE
         SYNTAX      OCTET STRING
         MAX-ACCESS  read-create
         STATUS      current
         DESCRIPTION
        "The Type of Service (TOS) Bits value. By definition, 
         the high-order three bits represent the IP precedence value, 
         whereas alternatively the high-order six bits represent the IP 
        Differentiated Services Code Point (DSCP) value.Valid values are 0x00-0xFF."
         ::= { apQosDsClassMapEntry 12 }

    apQosDsClassMapMatchIpTosMask OBJECT-TYPE
         SYNTAX      OCTET STRING
         MAX-ACCESS  read-create
         STATUS      current
         DESCRIPTION
       "The Type of Service (TOS) Mask value. By definition, 
         the high-order three bits represent the IP precedence value, 
         whereas alternatively the high-order six bits represent the IP 
        Differentiated Services Code Point (DSCP) value.  Therefore,
        a mask of 0xE0 is used for IP precedence, while mask of 0xFC
        is used for IP DSCP.Valid values are 0x00-0xFF."
         ::= { apQosDsClassMapEntry 13 }

    apQosDsClassMapMatchIpDscp OBJECT-TYPE
         SYNTAX      Integer32 (0..63)
         MAX-ACCESS  read-create
         STATUS      current
         DESCRIPTION
       "IP DiffServ Code Point (DSCP) match value for the class.  
        The DSCP is defined as the high-order six bits of the
        Service Type octet in the IPv4 header."
         ::= { apQosDsClassMapEntry 14 }

    apQosDsClassMapMatchIpPrecedence OBJECT-TYPE
         SYNTAX      Integer32 (0..7)
         MAX-ACCESS  read-create
         STATUS      current
         DESCRIPTION
                     "IP Precedence match value for the class.
        The Precedence bits are defined as the high-order three bits
        of the Service Type octed in the IPv4 header."
         ::= { apQosDsClassMapEntry 15 }

    apQosDsClassMapMatchProtocol OBJECT-TYPE
         SYNTAX      Integer32 (1..255)
         MAX-ACCESS  read-create
         STATUS      current
         DESCRIPTION
                     "icmp - 1
                      igmp - 2
                      ip - 4
                      tcp - 6
                      udp - 17
                      All values from 1 to 255 are valid."
         ::= { apQosDsClassMapEntry 16 }

    apQosDsClassMapMatchSrcMac OBJECT-TYPE
         SYNTAX      MacAddress
         MAX-ACCESS  read-create
         STATUS      current
         DESCRIPTION
                     "Source MAC address match value for the class."
         ::= { apQosDsClassMapEntry 17 }

    apQosDsClassMapMatchSrcMacMask OBJECT-TYPE
         SYNTAX      MacAddress
         MAX-ACCESS  read-create
         STATUS      current
         DESCRIPTION
       "Source MAC address mask match value for the class. This 
        mask value identifies the portion of
        apQosDsClassMapMatchSrcMac that is compared against a packet.
        A non-contiguous mask value is permitted."
         ::= { apQosDsClassMapEntry 18 }

    apQosDsClassMapMatchSrcIpAddress OBJECT-TYPE
         SYNTAX      InetAddress
         MAX-ACCESS  read-create
         STATUS      current
         DESCRIPTION
                     "The Source IP Address match value for the class."
         ::= { apQosDsClassMapEntry 19 }

    apQosDsClassMapMatchSrcIpMask OBJECT-TYPE
         SYNTAX      InetAddress
         MAX-ACCESS  read-create
         STATUS      current
         DESCRIPTION
       "Source IP address mask match value for the class. This 
        mask value identifies the portion of
        apQosDsClassMapMatchSrcIpAddress that is compared against
        a packet. A non-contiguous mask value is permitted."
         ::= { apQosDsClassMapEntry 20 }

    apQosDsClassMapMatchSrcL4Port OBJECT-TYPE
         SYNTAX      Integer32
         MAX-ACCESS  read-create
         STATUS      current
         DESCRIPTION
        "Source Port (Layer 4) used in class-map classification.
        Different port numbers are:
         ftpdata-20, ftp-21, telnet-23, smtp-25, domain-53, tftp-69, 
        http/www-80, snmp-161.All values from 0-65535 are valid."
         ::= { apQosDsClassMapEntry 21 }

    apQosDsClassMapMatchVlanId OBJECT-TYPE
         SYNTAX      Integer32 (0..4095) 
         MAX-ACCESS  read-create
         STATUS      current
         DESCRIPTION
        "Flag to indicate that class map is defined to match Vlan ID."
         ::= { apQosDsClassMapEntry 22 }

    apQosDsClassMapMatchCommit OBJECT-TYPE
         SYNTAX      Integer32 
         MAX-ACCESS  read-create
         STATUS      current
         DESCRIPTION
       "Flag to indicate that to apply all the class-map match
        attributes created for this row entry. This can be set only
        once. A value of 1 indicates commit operation for that
        particular class map creation. Once committed, the class map
        properties cannot be changed.The commit value after successful 
        commit is 3."
         ::= { apQosDsClassMapEntry 23 }

    apQosDsClassMapMatchFlags OBJECT-TYPE
         SYNTAX      Integer32
         MAX-ACCESS  read-only
         STATUS      current
         DESCRIPTION
       "Four byte to indicate the fields set for cos, ethertype,
        ip-tos, ip-dscp, ip-precedence. Each bit cos (1),
        ethertype (2), ip-tos (4), ip-dscp (8), ip-precedence (16)
        represents the corresponding field set.
        Other fields can be identified by getting the value."
         ::= { apQosDsClassMapEntry 24 }

    apQosDsClassMapMatchSrcIpv6Address OBJECT-TYPE
         SYNTAX      InetAddress
         MAX-ACCESS  read-create
         STATUS      current
         DESCRIPTION
        "The Source IPv6 Address match value for the class."
         ::= { apQosDsClassMapEntry 25 }

    apQosDsClassMapMatchSrcIpv6Prefix OBJECT-TYPE
         SYNTAX      Integer32 (0..128)
         MAX-ACCESS  read-create
         STATUS      current
         DESCRIPTION
        "The Source IPv6 Prefix length match value for the class."
         ::= { apQosDsClassMapEntry 26 }

   apQosDsClassMapMatchDstIpv6Address OBJECT-TYPE
         SYNTAX      InetAddress
         MAX-ACCESS  read-create
         STATUS      current
         DESCRIPTION
        "The Destination IPv6 Address match value for the class."
         ::= { apQosDsClassMapEntry 27 }

    apQosDsClassMapMatchDstIpv6Prefix OBJECT-TYPE
         SYNTAX      Integer32 (0..128)
         MAX-ACCESS  read-create
         STATUS      current
         DESCRIPTION
        "Destination IPv6 Prefix length match value for the class."
         ::= { apQosDsClassMapEntry 28 }

    apQosDsClassMapMatchIpv6FlowLabel OBJECT-TYPE
         SYNTAX      DisplayString
         MAX-ACCESS  read-create
         STATUS      current
         DESCRIPTION
        "The IPv6 Flow Label match value for the class.
        Hex values in the range of 00000 - FFFFF."
         ::= { apQosDsClassMapEntry 29 }


--*****************************************************************
--      apQosDsPolicyMapTable    OBJECT IDENTIFIER ::= { apQos 5 }
--*****************************************************************

    apQosDsPolicyMapTable OBJECT-TYPE
         SYNTAX      SEQUENCE OF ApQosDsPolicyMapEntry
         MAX-ACCESS  not-accessible
         STATUS      current
         DESCRIPTION
                     "A table of policy-map instances."
         ::= { apQos 5 }

    apQosDsPolicyMapEntry OBJECT-TYPE
         SYNTAX      ApQosDsPolicyMapEntry
         MAX-ACCESS  not-accessible
         STATUS      current
         DESCRIPTION
        "A policy-map instance entry."
         INDEX       { apQosDsPolicyMapName }
         ::= { apQosDsPolicyMapTable 1 }

ApQosDsPolicyMapEntry ::=
    SEQUENCE {
        apQosDsPolicyMapName            DisplayString,
        apQosDsPolicyMapStatus          RowStatus
       }

    apQosDsPolicyMapName OBJECT-TYPE
         SYNTAX      DisplayString (SIZE(1..31))
         MAX-ACCESS  not-accessible
         STATUS      current
         DESCRIPTION
        "Name of this policy-map entry, which must consist of 1 to 31
        alphanumeric characters and uniquely identify this class-map."
         ::= { apQosDsPolicyMapEntry 1 }

    apQosDsPolicyMapStatus OBJECT-TYPE
         SYNTAX      RowStatus
         MAX-ACCESS  read-create
         STATUS      current
         DESCRIPTION
                "Status of an entry. Supported values are:
                 - active (1)
                 - createAndGo (4)
                 
        The administrator can only use createAndGo, createAndWait,
        and destroy. After creating an entry, its status is moved
        to active."
         ::= { apQosDsPolicyMapEntry 2 }


--*****************************************************************
--      apQosDsPolicyMapAttrTable    OBJECT IDENTIFIER ::= { apQos 6 }
--*****************************************************************

    apQosDsPolicyMapAttrTable OBJECT-TYPE
         SYNTAX      SEQUENCE OF ApQosDsPolicyMapAttrEntry
         MAX-ACCESS  not-accessible
         STATUS      current
         DESCRIPTION
                     "A table of policy-map match attribute instances."
         ::= { apQos 6 }

    apQosDsPolicyMapAttrEntry OBJECT-TYPE
         SYNTAX      ApQosDsPolicyMapAttrEntry
         MAX-ACCESS  not-accessible
         STATUS      current
         DESCRIPTION
        "A policy-map match attribute instance entry."
         INDEX       { apQosDsPolicyMapName, apQosDsClassMapName, 
         apQosDsPolicyMapAttrPoliceSimple,apQosDsPolicyMapAttrIndex }
         ::= { apQosDsPolicyMapAttrTable 1 }

ApQosDsPolicyMapAttrEntry ::=
    SEQUENCE {
        apQosDsPolicyMapAttrIndex                       Integer32,
        apQosDsPolicyMapAttrPoliceSimple                TruthValue,
        apQosDsPolicyMapAttrDrop                        TruthValue,
        apQosDsPolicyMapAttrSend                        TruthValue,
        apQosDsPolicyMapAttrMarkCos                     Integer32,
        apQosDsPolicyMapAttrMarkIpDscp                  Integer32,
        apQosDsPolicyMapAttrMarkIpPrecedence            Integer32,
        apQosDsPolicyMapAttrStatus                      RowStatus,
        apQosDsPolicyMapAttrCommit                      Integer32,
        apQosDsPolicyMapAttrPolicyActionType            INTEGER,
        apQosDsPolicyMapAttrPoliceSimpleRate            Unsigned32,
        apQosDsPolicyMapAttrPoliceSimpleBurstSize       Integer32
        }

    apQosDsPolicyMapAttrIndex OBJECT-TYPE
         SYNTAX      Integer32
         MAX-ACCESS  not-accessible
         STATUS      current
         DESCRIPTION
        "Index of this match attribute instance within Diffserv."
         ::= { apQosDsPolicyMapAttrEntry 1 }

    apQosDsPolicyMapAttrPoliceSimple OBJECT-TYPE
         SYNTAX      TruthValue
         MAX-ACCESS  not-accessible
         STATUS      current
         DESCRIPTION
                     "Flag to indicate if police simple is turned on."
         ::= { apQosDsPolicyMapAttrEntry 2 }

    apQosDsPolicyMapAttrDrop OBJECT-TYPE
         SYNTAX      TruthValue
         MAX-ACCESS  read-create
         STATUS      current
         DESCRIPTION
       "Flag to indicate that all packets belonging to this
        class-instance are dropped. If set, no other action attribute
        needs to be configured."
         ::= { apQosDsPolicyMapAttrEntry 3 }

    apQosDsPolicyMapAttrSend OBJECT-TYPE
         SYNTAX      TruthValue
         MAX-ACCESS  read-create
         STATUS      current
         DESCRIPTION
       "Flag to indicate that all packets belonging to this
        class-instance are forwarded. If set, no other action
        attribute needs to be configured."
         ::= { apQosDsPolicyMapAttrEntry 4 }

    apQosDsPolicyMapAttrMarkCos OBJECT-TYPE
         SYNTAX      Integer32 (0..7)
         MAX-ACCESS  read-create
         STATUS      current
         DESCRIPTION
        "Three-bit user priority field value in the 802.1Q tag header
        of a tagged Ethernet frame, marked as part of the policy for a
        class instance. If set, no other action attribute needs to be
        configured."
         ::= { apQosDsPolicyMapAttrEntry 5 }

    apQosDsPolicyMapAttrMarkIpDscp OBJECT-TYPE
         SYNTAX      Integer32 (0..63)
         MAX-ACCESS  read-create
         STATUS      current
         DESCRIPTION
       "Specified IP DSCP value to mark in all packets belonging
        to the class-instance. If set, no other action attribute
        needs to be configured."
         ::= { apQosDsPolicyMapAttrEntry 6 }

    apQosDsPolicyMapAttrMarkIpPrecedence OBJECT-TYPE
         SYNTAX      Integer32 (0..7)
         MAX-ACCESS  read-create
         STATUS      current
         DESCRIPTION
       "Specified IP Precedence value to mark in all packets 
        belonging to the class-instance. If set, no other action
        attribute needs to be configured."
         ::= { apQosDsPolicyMapAttrEntry 7 }

    apQosDsPolicyMapAttrStatus OBJECT-TYPE
         SYNTAX      RowStatus
         MAX-ACCESS  read-create
         STATUS      current
         DESCRIPTION
                "Status of an entry. Supported values are:
                 - active (1)
                 - createAndGo (4)
                 - destroy (6)

        The administrator can only use createAndGo, createAndWait,
        and destroy. After creating an entry, its status is moved
        to active."
         ::= { apQosDsPolicyMapAttrEntry 8 }

    apQosDsPolicyMapAttrCommit OBJECT-TYPE
         SYNTAX      Integer32 
         MAX-ACCESS  read-create
         STATUS      current
         DESCRIPTION
       "Flag to indicate that to apply all the policy attributes 
        created for this row entry. This can be set only once.
        Once the attributes are committed they cannot be changed
        for that particular policy map and class map combination.
        The commit value after successful commit is 3."
         ::= { apQosDsPolicyMapAttrEntry 9 }

    apQosDsPolicyMapAttrPolicyActionType OBJECT-TYPE
         SYNTAX      INTEGER {
                      drop(1),
                      send(2),
                      cos(3),
                      ipdscp(4),
                      ipprecedence(5)
                     }
         MAX-ACCESS  read-only
         STATUS      current
         DESCRIPTION
        "Policy map match entry type. It determines which one of the
        individual match conditions is defined for the present
        policy map attribute."
         ::= { apQosDsPolicyMapAttrEntry 10 }

    apQosDsPolicyMapAttrPoliceSimpleRate OBJECT-TYPE
         SYNTAX      Unsigned32 (1..1000000)
         MAX-ACCESS  read-create
         STATUS      current
         DESCRIPTION
        "Policy Attribute Rate configured in kbps.
        It is used when police simple is turned on."
         ::= { apQosDsPolicyMapAttrEntry 11 }

    apQosDsPolicyMapAttrPoliceSimpleBurstSize OBJECT-TYPE
         SYNTAX      Integer32 (1..204800000)
         MAX-ACCESS  read-create
         STATUS      current
         DESCRIPTION
        "Policy Attribute Burst Size in bytes.
        It is used when police simple is turned on."
         ::= { apQosDsPolicyMapAttrEntry 12 }


--*****************************************************************
--      apQosMacAclTable    OBJECT IDENTIFIER ::= { apQos 7 }
--*****************************************************************

    apQosMacAclTable OBJECT-TYPE
         SYNTAX      SEQUENCE OF ApQosMacAclEntry
         MAX-ACCESS  not-accessible
         STATUS      current
         DESCRIPTION
                     "A table of MAC-ACL instances."
         ::= { apQos 7 }

    apQosMacAclEntry OBJECT-TYPE
         SYNTAX      ApQosMacAclEntry
         MAX-ACCESS  not-accessible
         STATUS      current
         DESCRIPTION
        "A MAC-ACL instance entry."
         INDEX       { apQosMacAclName }
         ::= { apQosMacAclTable 1 }

ApQosMacAclEntry ::=
    SEQUENCE {
        apQosMacAclName         DisplayString,
        apQosMacAclStatus       RowStatus
        }

    apQosMacAclName OBJECT-TYPE
         SYNTAX      DisplayString (SIZE(1..31))
         MAX-ACCESS  not-accessible
         STATUS      current
         DESCRIPTION
        "Name of this MAC ACL entry, which must consist of 1 to 31
        alphanumeric characters and uniquely identify this MAC ACL.
        This object must be set to complete a new MAC ACL instance."
         ::= { apQosMacAclEntry 1 }

    apQosMacAclStatus OBJECT-TYPE
         SYNTAX      RowStatus
         MAX-ACCESS  read-create
         STATUS      current
         DESCRIPTION
                "Status of an entry. Supported values are:
                 - active (1)
                 - createAndGo (4)
                 - destroy (6)

        The administrator can only use createAndGo, createAndWait,
        and destroy. After creating an entry, its status is moved
        to active."
         ::= { apQosMacAclEntry 2 }


--*****************************************************************
--      apQosMacRuleTable    OBJECT IDENTIFIER ::= { apQos 8 }
--*****************************************************************

    apQosMacRuleTable OBJECT-TYPE
         SYNTAX      SEQUENCE OF ApQosMacRuleEntry
         MAX-ACCESS  not-accessible
         STATUS      current
         DESCRIPTION
                     "A table of MAC-ACL rule instances."
         ::= { apQos 8 }

    apQosMacRuleEntry OBJECT-TYPE
         SYNTAX      ApQosMacRuleEntry
         MAX-ACCESS  not-accessible
         STATUS      current
         DESCRIPTION
        "A MAC-ACL rule instance entry."
         INDEX       {apQosMacAclName,apQosMacAclRuleIndex}
         ::= { apQosMacRuleTable 1 }

ApQosMacRuleEntry ::=
    SEQUENCE {
        apQosMacAclRuleIndex                    Integer32,
        apQosMacAclRuleAction                   INTEGER,
        apQosMacAclRuleStatus                   RowStatus,
        apQosMacAclRuleMatchEvery               TruthValue,
        apQosMacAclRuleMatchDstMac              MacAddress,
        apQosMacAclRuleMatchDstMacMask          MacAddress,
        apQosMacAclRuleMatchCos                 Integer32,
        apQosMacAclRuleMatchEthertype           DisplayString,
        apQosMacAclRuleMatchSrcMac              MacAddress,
        apQosMacAclRuleMatchSrcMacMask          MacAddress,
        apQosMacAclRuleMatchVlanId              Integer32,
        apQosMacAclRuleMatchCommit              Integer32
        }

    apQosMacAclRuleIndex OBJECT-TYPE
         SYNTAX      Integer32
         MAX-ACCESS  not-accessible
         STATUS      current
         DESCRIPTION
        "Index of this rule instance within a MAC ACL."
         ::= { apQosMacRuleEntry 1 }

     apQosMacAclRuleAction OBJECT-TYPE
         SYNTAX      INTEGER {
                      permit(1),
                      deny(2)
                      }
         MAX-ACCESS  read-create
         STATUS      current
         DESCRIPTION
                     "The type of action this rule should perform."
         DEFVAL { deny }
         ::= { apQosMacRuleEntry 2 }

    apQosMacAclRuleStatus OBJECT-TYPE
         SYNTAX      RowStatus
         MAX-ACCESS  read-create
         STATUS      current
         DESCRIPTION
                "Status of an entry. Supported values are:
                 - active (1)
                 - createAndGo (4)

        The administrator can only use createAndGo and createAndWait. 
        After creating an entry, its status is moved to active."
         ::= { apQosMacRuleEntry 3 }

    apQosMacAclRuleMatchEvery OBJECT-TYPE
         SYNTAX      TruthValue
         MAX-ACCESS  read-create
         STATUS      current
         DESCRIPTION
        "Flag to indicate that the match attribute is defined to match
        on packet, regardless of content. If set to true(1), all other
        classification field objects in this row are ignored.
        Error is returned for all other values set."
         DEFVAL { false }
         ::= { apQosMacRuleEntry 4 }

    apQosMacAclRuleMatchDstMac OBJECT-TYPE
         SYNTAX      MacAddress
         MAX-ACCESS  read-create
         STATUS      current
         DESCRIPTION
        "Destination MAC address match value for the Rule."
         ::= { apQosMacRuleEntry 5 }

    apQosMacAclRuleMatchDstMacMask OBJECT-TYPE
         SYNTAX      MacAddress
         MAX-ACCESS  read-create
         STATUS      current
         DESCRIPTION
        "Destination MAC address mask match value for the Rule."
         ::= { apQosMacRuleEntry 6 }

    apQosMacAclRuleMatchCos OBJECT-TYPE
         SYNTAX      Integer32 (0..7)
         MAX-ACCESS  read-create
         STATUS      current
         DESCRIPTION
        "Three-bit user priority field in the 802.1Q tag header 
         of a tagged Ethernet frame used as a rule-match parameter."
         ::= { apQosMacRuleEntry 7 }

    apQosMacAclRuleMatchEthertype OBJECT-TYPE
         SYNTAX      DisplayString
         MAX-ACCESS  read-create
         STATUS      current
         DESCRIPTION
        "The Ethertype match value for the class. Hex values in the
         range of 0x0600-0xFFFF. Different ethertype key values are
         appletalk(0x02), arp(0x03), ibmsna(0x04), ipv4(0x05), ipv6(0x06),
         ipx(0x07), mplsmcast(0x08), mplsucast(0x09), netbios(0x0a), novell(0x0b),
         pppoe(0x0c), rarp(0x0d)."
         ::= { apQosMacRuleEntry 8 }

    apQosMacAclRuleMatchSrcMac OBJECT-TYPE
         SYNTAX      MacAddress
         MAX-ACCESS  read-create
         STATUS      current
         DESCRIPTION
                     "Source MAC address match value for the rule."
         ::= { apQosMacRuleEntry 9 }

    apQosMacAclRuleMatchSrcMacMask OBJECT-TYPE
         SYNTAX      MacAddress
         MAX-ACCESS  read-create
         STATUS      current
         DESCRIPTION
        "Source MAC address mask match value for the rule. This mask
        value identifies the portion of apQosMacAclRuleMatchSrcMac
        that is compared against a packet. A non-contiguous mask
        value is permitted."
         ::= { apQosMacRuleEntry 10 }

    apQosMacAclRuleMatchVlanId OBJECT-TYPE
         SYNTAX      Integer32 (0..4095) 
         MAX-ACCESS  read-create
         STATUS      current
         DESCRIPTION
        "Flag to indicate that the rule is defined to match Vlan ID."
         ::= { apQosMacRuleEntry 11 }

    apQosMacAclRuleMatchCommit OBJECT-TYPE
         SYNTAX      Integer32 
         MAX-ACCESS  read-create
         STATUS      current
         DESCRIPTION
        "Flag to indicate that to apply all the rule match attributes
        created for this row entry. This can be set only once.
        Once committed, the rule properties cannot be changed.The
        commit value after successful commit is 3."
         ::= { apQosMacRuleEntry 12 }
--*****************************************************************
--      apTspecAcmTable      OBJECT IDENTIFIER ::= { apTspecTables 1 }                            
--*****************************************************************

apTspecAcmTable OBJECT-TYPE
    SYNTAX      SEQUENCE OF ApTspecAcmEntry
    MAX-ACCESS  not-accessible
    STATUS      current
    DESCRIPTION
            "TSPEC Admission Control Mandatory (ACM) configuration
             parameters."
    ::= { apTspecTables 1}

apTspecAcmEntry OBJECT-TYPE
    SYNTAX      ApTspecAcmEntry
    MAX-ACCESS  not-accessible
    STATUS      current
    DESCRIPTION
            "TSPEC Admission Control Mandatory (ACM) configuration 
             parameters (per radio)."
    INDEX       {apTspecRadioName}
    ::= { apTspecAcmTable 1 }

ApTspecAcmEntry ::=
    SEQUENCE {
	apTspecRadioName	    DisplayString,
        apTspecStatus               RowStatus,
        apTspecMode                 INTEGER,
        apTspecVoiceAcmMode         INTEGER,
        apTspecVoiceAcmLimit        INTEGER,
        apTspecVideoAcmMode         INTEGER,
        apTspecVideoAcmLimit        INTEGER,
        apTspecApInactivityTimeout  INTEGER,
        apTspecStaInactivityTimeout INTEGER,
        apTspecLegacyWmmQMapMode    INTEGER
    }

apTspecRadioName OBJECT-TYPE
    SYNTAX      DisplayString
    MAX-ACCESS  not-accessible
    STATUS      current
    DESCRIPTION
            "AP radio name."
    ::= { apTspecAcmEntry 1 }

apTspecStatus  OBJECT-TYPE
        SYNTAX          RowStatus
        MAX-ACCESS      read-create
        STATUS          current
        DESCRIPTION             
                "Status of the entry. 
                 Only values active (1), createAndGo (4),
                 createAndWait (5) and destroy (6) are supported. 
                 The Administrator can only use createAndGo, createAndWait and 
                 destroy. After creating the entry, the status is moved to
                 active (1)"
        ::= { apTspecAcmEntry 2 }

apTspecMode  OBJECT-TYPE
        SYNTAX INTEGER
               {
                 on(1),
                 off(2)
               }
        MAX-ACCESS read-write
        STATUS current
        DESCRIPTION
                "Overall TSPEC operational mode for the designated apTspecRadioName.
                 This object must be set to on(1) for any of the other TSPEC ACM 
                 configuration parameters to have an effect.  The default value
                 for this object is off(2)."
        DEFVAL      { off }
        ::= { apTspecAcmEntry 3}

apTspecVoiceAcmMode  OBJECT-TYPE
        SYNTAX INTEGER
               {
                 on(1),
                 off(2)
               }
        MAX-ACCESS read-write
        STATUS current
        DESCRIPTION
                "Regulates mandatory admission control for the voice
                 access category (AC).  When set to on(1), the
                 voice AC may only be used by WMM-compliant client
                 stations that have successfully established a TSPEC
                 for this AC.

                 Note that setting the apTspecLegacyWmmQMapMode
                 object to on(1) overrides the exclusive use of the 
                 voice AC by allowing legacy (i.e. non-WMM-compliant) client
                 stations to use it as well."
        DEFVAL      { off }
        ::= { apTspecAcmEntry 4}

apTspecVoiceAcmLimit  OBJECT-TYPE
        SYNTAX INTEGER(0..70)
        MAX-ACCESS read-write
        STATUS current
        DESCRIPTION
                "Defines the maximum amount of wireless bandwidth utilization to admit
                 for the voice access category.  TSPEC requests that would cause
                 this limit to be exceeded are rejected.

                 Note that this value establishes an upper limit for wireless bandwidth
                 to be admitted for this access category but does not guarantee that this
                 limit can be reached.

                 Setting this object value to 0 and the apTspecVoiceAcmMode object
                 to on(1) causes all TSPEC requests to be rejected by the AP for the
                 voice access category.

                 The sum of this value and the apTspecVideoAcmLimit object value 
                 is not allowed to exceed 70.

                 This value is treated as a percentage."
        DEFVAL      { 20 }
        ::= { apTspecAcmEntry 5}

apTspecVideoAcmMode  OBJECT-TYPE
        SYNTAX INTEGER
               {
                 on(1),
                 off(2)
               }
        MAX-ACCESS read-write
        STATUS current
        DESCRIPTION
                "Regulates mandatory admission control for the video
                 access category (AC).  When set to on(1), the
                 voice AC may only be used by WMM-compliant client
                 stations that have successfully established a TSPEC
                 for this AC.

                 Note that setting the apTspecLegacyWmmQMapMode
                 object to on(1) overrides the exclusive use of the 
                 video AC by allowing legacy (i.e. non-WMM-compliant) client
                 stations to use it as well."
        DEFVAL      { off }
        ::= { apTspecAcmEntry 6}

apTspecVideoAcmLimit  OBJECT-TYPE
        SYNTAX INTEGER(0..70)
        MAX-ACCESS read-write
        STATUS current
        DESCRIPTION
                "Defines the maximum amount of wireless bandwidth utilization to admit
                 for the video access category.  TSPEC requests that would cause
                 this limit to be exceeded are rejected.

                 Note that this value establishes an upper limit for wireless bandwidth
                 to be admitted for this access category but does not guarantee that this
                 limit can be reached.

                 Setting this object value to 0 and the apTspecVideoAcmMode object
                 to on(1) causes all TSPEC requests to be rejected by the AP for the
                 voice access category.

                 The sum of this value and the apTspecVoiceAcmLimit object value 
                 is not allowed to exceed 70.

                 This value is treated as a percentage."
        DEFVAL      { 15 }
        ::= { apTspecAcmEntry 7}

apTspecApInactivityTimeout  OBJECT-TYPE
        SYNTAX INTEGER(0..120)
        MAX-ACCESS read-write
        STATUS current
        DESCRIPTION
                "Specifies the amount of time that an active traffic stream (TS)
                 in the downlink direction may be idle, from the perspective of
                 the AP, before it is deleted by the AP.

                 For a bidirectional TS, both the apTspecApInactivityTimeout
                 and the apTspecStaInactivityTimeout must expire in order 
                 for the TS to be deleted by the AP due to inactivity.  If either 
                 of these timeouts is disabled, the AP will not delete a 
                 bidirectional TS due to inactivity.
                  
                 This value is specified in seconds.  Setting this object value
                 to 0 disables this timeout."
        DEFVAL      { 30 }
        ::= { apTspecAcmEntry 8}

apTspecStaInactivityTimeout  OBJECT-TYPE
        SYNTAX INTEGER(0..120)
        MAX-ACCESS read-write
        STATUS current
        DESCRIPTION
                "Specifies the amount of time that an active traffic stream (TS)
                 in the uplink direction may be idle, from the perspective of
                 the AP, before it is deleted by the AP.

                 For a bidirectional TS, both the apTspecApInactivityTimeout
                 and the apTspecStaInactivityTimeout must expire in order 
                 for the TS to be deleted by the AP due to inactivity.  If either 
                 of these timeouts is disabled, the AP will not delete a 
                 bidirectional TS due to inactivity.
                  
                 This value is specified in seconds.  Setting this object value
                 to 0 disables this timeout."
        DEFVAL      { 30 }
        ::= { apTspecAcmEntry 9}

apTspecLegacyWmmQMapMode  OBJECT-TYPE
        SYNTAX INTEGER
               {
                 on(1),
                 off(2)
               }
        MAX-ACCESS read-write
        STATUS current
        DESCRIPTION
                "When set to on(1), the AP allows intermixing of legacy traffic
                 with Wi-Fi Multimedia (WMM) traffic on access category
                 queues that are operating according to admission control
                 mandatory (ACM) rules.

                 This mode is intended for use with non Wi-Fi Multimedia Enabled
                 (non-WME) clients and is off(2) by default.  When this object
                 is set to on(1), both the voice and video access categories
                 are accessible by wireless clients that do not have an admitted 
                 TSPEC, which can lead to underestimation of the available medium
                 time by wireless TSPEC admission control. Use caution when enabling
                 this mode and also consider using very small ACM limit values as well."
        DEFVAL      { off }
        ::= { apTspecAcmEntry 10}



--*****************************************************************
--  apTspec         OBJECT IDENTIFIER ::= { apTspecTables 2 }
--*****************************************************************

apTspecVoAccept         OBJECT-TYPE
        SYNTAX          INTEGER
        MAX-ACCESS      read-only
        STATUS          current
        DESCRIPTION
                "Total number of voice TSPECs accepted by this AP."
        ::= { apTspec 1 }

apTspecVoReject         OBJECT-TYPE
        SYNTAX          INTEGER
        MAX-ACCESS      read-only
        STATUS          current
        DESCRIPTION
                "Total number of voice TSPECs rejected by this AP."
        ::= { apTspec 2 }
apTspecViAccept         OBJECT-TYPE
        SYNTAX          INTEGER
        MAX-ACCESS      read-only
        STATUS          current
        DESCRIPTION
                "Total number of video TSPECs accepted by this AP."
        ::= { apTspec 3 }

apTspecViReject         OBJECT-TYPE
        SYNTAX          INTEGER
        MAX-ACCESS      read-only
        STATUS          current
        DESCRIPTION
                "Total number of video TSPECs rejected by this AP."
        ::= { apTspec 4 }

--*****************************************************************
--      apTspecAcmRadioTable      OBJECT IDENTIFIER ::= { apTspecTables 3 }                            
--*****************************************************************

apTspecAcmRadioTable OBJECT-TYPE
    SYNTAX      SEQUENCE OF ApTspecAcmRadioEntry
    MAX-ACCESS  not-accessible
    STATUS      current
    DESCRIPTION
            "TSPEC Admission Control Mandatory (ACM) status
             per radio."
    ::= { apTspecTables 3}

apTspecAcmRadioEntry OBJECT-TYPE
    SYNTAX      ApTspecAcmRadioEntry
    MAX-ACCESS  not-accessible
    STATUS      current
    DESCRIPTION
            "An entry for TSPEC Admission Control Mandatory (ACM) status
             per radio."
    INDEX       {apTspecAcmRadioName,apTspecAC}
    ::= { apTspecAcmRadioTable 1 }

ApTspecAcmRadioEntry ::=
    SEQUENCE {
	apTspecAcmRadioName	    DisplayString,
	apTspecAC	            DisplayString,
        apTspecOperStatus           DisplayString,
        apTspecActiveTS             INTEGER,
        apTspecActiveClients        INTEGER,
        apTspecMediumTimeAdmitted   INTEGER,
        apTspecMediumTimeUnalloc    INTEGER,
	apTspecTxBytes		    INTEGER,
	apTspecTxPackets	    INTEGER,
	apTspecRxBytes		    INTEGER,
	apTspecRxPackets	    INTEGER
    }

apTspecAcmRadioName OBJECT-TYPE
    SYNTAX      DisplayString
    MAX-ACCESS  not-accessible
    STATUS      current
    DESCRIPTION
            "AP radio name."
    ::= { apTspecAcmRadioEntry 1 }

apTspecAC OBJECT-TYPE
    SYNTAX      DisplayString
    MAX-ACCESS  not-accessible
    STATUS      current
    DESCRIPTION
            "AP TSPEC access category (AC)."
    ::= { apTspecAcmRadioEntry 2 }

apTspecOperStatus OBJECT-TYPE
        SYNTAX DisplayString
        MAX-ACCESS read-only
        STATUS current
        DESCRIPTION
                "TSPEC operational status per access category."
        ::= { apTspecAcmRadioEntry 3}

apTspecActiveTS  OBJECT-TYPE
        SYNTAX INTEGER
        MAX-ACCESS read-only
        STATUS current
        DESCRIPTION
                "Number of active traffic streams (TSs)."
        ::= { apTspecAcmRadioEntry 4}

apTspecActiveClients  OBJECT-TYPE
        SYNTAX INTEGER
        MAX-ACCESS read-only
        STATUS current
        DESCRIPTION
                "Number of active clients with at least one traffic stream
                 on this radio."
        ::= { apTspecAcmRadioEntry 5}
apTspecMediumTimeAdmitted  OBJECT-TYPE
        SYNTAX INTEGER
        MAX-ACCESS read-only
        STATUS current
        DESCRIPTION
                "Sum of all medium times currently admitted 
                 for this access category."
        ::= { apTspecAcmRadioEntry 6}
apTspecMediumTimeUnalloc  OBJECT-TYPE
        SYNTAX INTEGER
        MAX-ACCESS read-only
        STATUS current
        DESCRIPTION
                "Amount of configured medium time that is not allocated 
                 for this access category."
        ::= { apTspecAcmRadioEntry 7}

apTspecTxBytes  OBJECT-TYPE
        SYNTAX INTEGER
        MAX-ACCESS read-only
        STATUS current
        DESCRIPTION
                "Total bytes transmitted for this access category."
        ::= { apTspecAcmRadioEntry 8}
apTspecTxPackets  OBJECT-TYPE
        SYNTAX INTEGER
        MAX-ACCESS read-only
        STATUS current
        DESCRIPTION
                "Total packets transmitted for this access category."
        ::= { apTspecAcmRadioEntry 9}
apTspecRxBytes  OBJECT-TYPE
        SYNTAX INTEGER
        MAX-ACCESS read-only
        STATUS current
        DESCRIPTION
                "Total bytes received for this access category."
        ::= { apTspecAcmRadioEntry 10}
apTspecRxPackets  OBJECT-TYPE
        SYNTAX INTEGER
        MAX-ACCESS read-only
        STATUS current
        DESCRIPTION
                "Total packets received for this access category."
        ::= { apTspecAcmRadioEntry 11}

--*****************************************************************
--      apTspecAcmVapTable      OBJECT IDENTIFIER ::= { apTspecTables 4 }                            
--*****************************************************************

apTspecAcmVapTable OBJECT-TYPE
    SYNTAX      SEQUENCE OF ApTspecAcmVapEntry
    MAX-ACCESS  not-accessible
    STATUS      current
    DESCRIPTION
            "TSPEC Admission Control Mandatory (ACM) status
             per VAP."
    ::= { apTspecTables 4}

apTspecAcmVapEntry OBJECT-TYPE
    SYNTAX      ApTspecAcmVapEntry
    MAX-ACCESS  not-accessible
    STATUS      current
    DESCRIPTION
            "An entry for TSPEC Admission Control Mandatory (ACM) status
             per VAP."
    INDEX       {apTspecVapRadioName,apTspecVap,apTspecVapAC}
    ::= { apTspecAcmVapTable 1 }

ApTspecAcmVapEntry ::=
    SEQUENCE {
	apTspecVapRadioName	    DisplayString,
	apTspecVap	            DisplayString,
	apTspecVapAC	            DisplayString,
        apTspecVapOperStatus           DisplayString,
        apTspecVapActiveTS             INTEGER,
        apTspecVapActiveClients        INTEGER,
        apTspecVapMediumTimeAdmitted   INTEGER,
        apTspecVapMediumTimeUnalloc    INTEGER
    }

apTspecVapRadioName OBJECT-TYPE
    SYNTAX      DisplayString
    MAX-ACCESS  not-accessible
    STATUS      current
    DESCRIPTION
            "AP radio name."
    ::= { apTspecAcmVapEntry 1 }

apTspecVap OBJECT-TYPE
    SYNTAX      DisplayString
    MAX-ACCESS  not-accessible
    STATUS      current
    DESCRIPTION
            "Virtual AP name."
    ::= { apTspecAcmVapEntry 2 }

apTspecVapAC OBJECT-TYPE
    SYNTAX      DisplayString
    MAX-ACCESS  not-accessible
    STATUS      current
    DESCRIPTION
            "AP TSPEC access category (AC)."
    ::= { apTspecAcmVapEntry 3 }

apTspecVapOperStatus OBJECT-TYPE
        SYNTAX DisplayString
        MAX-ACCESS read-only
        STATUS current
        DESCRIPTION
                "TSPEC operational status per access category."
        ::= { apTspecAcmVapEntry 4}

apTspecVapActiveTS  OBJECT-TYPE
        SYNTAX INTEGER
        MAX-ACCESS read-only
        STATUS current
        DESCRIPTION
                "Number of active traffic streams (TSs)."
        ::= { apTspecAcmVapEntry 5}

apTspecVapActiveClients  OBJECT-TYPE
        SYNTAX INTEGER
        MAX-ACCESS read-only
        STATUS current
        DESCRIPTION
                "Number of active clients with at least one traffic stream
                 on this VAP."
        ::= { apTspecAcmVapEntry 6}
apTspecVapMediumTimeAdmitted  OBJECT-TYPE
        SYNTAX INTEGER
        MAX-ACCESS read-only
        STATUS current
        DESCRIPTION
                "Sum of all medium times currently admitted 
                 for this access category."
        ::= { apTspecAcmVapEntry 7}
apTspecVapMediumTimeUnalloc  OBJECT-TYPE
        SYNTAX INTEGER
        MAX-ACCESS read-only
        STATUS current
        DESCRIPTION
                "Amount of configured medium time that is not allocated
                 for this access category."
        ::= { apTspecAcmVapEntry 8}

--*****************************************************************
--  apTspecConfig         OBJECT IDENTIFIER ::= { apTspecTables 5 }
--*****************************************************************

apTspecViolationInterval         OBJECT-TYPE
        SYNTAX          INTEGER
        MAX-ACCESS      read-write
        STATUS          current
        DESCRIPTION
                "Specifies the time period at which wireless
                 clients detected as using admission-controlled 
                 resources without proper TSPEC authorization are
                 reported via the system logging and SNMP trap
                 mechanisms.

                 This object is specified in seconds, with a default 
                 value of 300 (5 minutes).  Setting this object value 
                 to 0 disables TSPEC violation reporting."
       DEFVAL      { 300 }
        ::= { apTspecConfig 1 }


--*****************************************************************
--  apTspecTrap         OBJECT IDENTIFIER ::= { apTspecTables 7 }
--*****************************************************************
apTspecTrap        OBJECT IDENTIFIER
                ::= { apTspecTables 7}

apTspecTrapPrefix       OBJECT IDENTIFIER
                ::= { apTspecTrap 0 }

apTspecTrapObjects      OBJECT IDENTIFIER
                ::= { apTspecTrap 1 }


apTspecTrapSeverity     OBJECT-TYPE
SYNTAX          SnmpAdminString
MAX-ACCESS      accessible-for-notify
STATUS          current
DESCRIPTION     "This string contains severity of trap message."
::= {apTspecTrapObjects 1 }
apTspecTrapMessage      OBJECT-TYPE
SYNTAX          SnmpAdminString
MAX-ACCESS      accessible-for-notify
STATUS          current
DESCRIPTION     "This string contains contents of trap message."
::= { apTspecTrapObjects        2 }

apTspecTrapMacAddress   OBJECT-TYPE
SYNTAX          SnmpAdminString
MAX-ACCESS      accessible-for-notify
STATUS          current
DESCRIPTION     "This string contains the client MAC address."
::= { apTspecTrapObjects        3 }

apTspecTrapAccessCategory       OBJECT-TYPE
SYNTAX          SnmpAdminString
MAX-ACCESS      accessible-for-notify
STATUS          current
DESCRIPTION     "This string contains the Access-Category(Voice/Video) of the TS."
::= { apTspecTrapObjects        4}
apTspecTrapDirection    OBJECT-TYPE
SYNTAX          SnmpAdminString
MAX-ACCESS      accessible-for-notify
STATUS          current
DESCRIPTION     "This string contains the direction of the TS"
::= { apTspecTrapObjects        5 }

apTspecTrapMediumTime   OBJECT-TYPE
SYNTAX          SnmpAdminString
MAX-ACCESS      accessible-for-notify
STATUS          current
DESCRIPTION     "This string contains the medium time of the TS."
::= { apTspecTrapObjects        6 }

apTspecTrapTid   OBJECT-TYPE
SYNTAX          SnmpAdminString
MAX-ACCESS      accessible-for-notify
STATUS          current
DESCRIPTION     "This string contains the tid of the TS."
::= { apTspecTrapObjects        7}

apTspecTrapNotification NOTIFICATION-TYPE
OBJECTS         { apTspecTrapSeverity,
                  apTspecTrapMessage,
                  apTspecTrapMacAddress,
                  apTspecTrapAccessCategory,
                  apTspecTrapDirection,
                  apTspecTrapMediumTime,
                  apTspecTrapTid}
STATUS          current
DESCRIPTION     "Object which contains information about the TSPEC client."
::= { apTspecTrapPrefix 1 }


--*****************************************************************
--  apTspecUnAuthTrafficTrap         OBJECT IDENTIFIER ::= { apTspecTables 8 }
--*****************************************************************
apTspecUnAuthTrafficTrap        OBJECT IDENTIFIER
                ::= { apTspecTables 8}

apTspecUnAuthTrafficTrapPrefix       OBJECT IDENTIFIER
                ::= { apTspecUnAuthTrafficTrap 0 }

apTspecUnAuthTrafficTrapObjects      OBJECT IDENTIFIER
                ::= { apTspecUnAuthTrafficTrap 1 }


apTspecUnAuthTrafficTrapSeverity     OBJECT-TYPE
SYNTAX          SnmpAdminString
MAX-ACCESS      accessible-for-notify
STATUS          current
DESCRIPTION     "This string contains severity of trap message."
::= {apTspecUnAuthTrafficTrapObjects 1 }
apTspecUnAuthTrafficTrapMessage      OBJECT-TYPE
SYNTAX          SnmpAdminString
MAX-ACCESS      accessible-for-notify
STATUS          current
DESCRIPTION     "This string contains contents of trap message."
::= { apTspecUnAuthTrafficTrapObjects        2 }

apTspecUnAuthTrafficTrapMacAddress   OBJECT-TYPE
SYNTAX          SnmpAdminString
MAX-ACCESS      accessible-for-notify
STATUS          current
DESCRIPTION     "This string contains the client MAC address."
::= { apTspecUnAuthTrafficTrapObjects        3 }

apTspecUnAuthTrafficTrapAccessCategory       OBJECT-TYPE
SYNTAX          SnmpAdminString
MAX-ACCESS      accessible-for-notify
STATUS          current
DESCRIPTION     "This string contains the Access-Category(Voice/Video) of the TS."
::= { apTspecUnAuthTrafficTrapObjects        4}

apTspecUnAuthTrafficTrapNotification NOTIFICATION-TYPE
OBJECTS         { apTspecUnAuthTrafficTrapSeverity,
                  apTspecUnAuthTrafficTrapMessage,
                  apTspecUnAuthTrafficTrapMacAddress,
                  apTspecUnAuthTrafficTrapAccessCategory}
STATUS          current
DESCRIPTION     "Object which contains information about the TSPEC client."
::= { apTspecUnAuthTrafficTrapPrefix 1 }
--*****************************************************************
--  apPacketCaptureStatusInfo OBJECT IDENTIFIER ::= { apPacketCapture 1}
--*****************************************************************

apPacketCaptureStatus OBJECT-TYPE
    SYNTAX  DisplayString
    MAX-ACCESS  read-only
    STATUS      current
    DESCRIPTION
            "Current packet capture status. States are
              Not Started
              File Capture In Progress
              Remote Capture In Progress
              Stopped due to Timeout
              Stopped due to File Size
              Stopped due to Administration Action
              Not Started due to File Transfer"
    ::= { apPacketCaptureStatusInfo 1 }

apPacketCaptureTime OBJECT-TYPE
    SYNTAX  DisplayString
    MAX-ACCESS  read-only
    STATUS      current
    DESCRIPTION
            "Elapsed time since packet capture started."
    ::= { apPacketCaptureStatusInfo 2 }

apPacketCaptureFileSize OBJECT-TYPE
    SYNTAX  INTEGER
    MAX-ACCESS  read-only
    STATUS      current
    DESCRIPTION
            "Current packet capture file size (valid for file capture only)."
    ::= { apPacketCaptureStatusInfo 3 }

apPacketCaptureDownloadStatus OBJECT-TYPE
    SYNTAX  INTEGER {
        notStarted(1), 
        inProgress(2), 
        success(3), 
        failed(4)
    }
    MAX-ACCESS  read-only
    STATUS      current
    DESCRIPTION
            "Packet capture file download status."
    ::= { apPacketCaptureStatusInfo 4 }

apPacketCaptureAdminStop OBJECT-TYPE
    SYNTAX  INTEGER {
            none(1),
            stop(2)
    }
    MAX-ACCESS  read-write
    STATUS      current
    DESCRIPTION
            "This is an action object.Setting this object to stop will
	    stop file or remote packet capture.Read on this object will always return none."
    ::= { apPacketCaptureStatusInfo 5 }

--*****************************************************************
--  apPacketCaptureConfig     OBJECT IDENTIFIER ::= { apPacketCapture 2}
--*****************************************************************

apPktCaptureCfgBeaconCapture OBJECT-TYPE
    SYNTAX  INTEGER {
        enable(1), 
        disable(2)
    }
    MAX-ACCESS  read-write
    STATUS      current
    DESCRIPTION
            "When packets are captured on radio1 or radio2 interface,
	     beacon frames are also captured."
    ::= { apPacketCaptureConfig 1 }

apPktCaptureCfgPromiscuousMode OBJECT-TYPE
    SYNTAX  INTEGER {
        enable(1), 
        disable(2)
    }
    MAX-ACCESS  read-write
    STATUS      current
    DESCRIPTION
            "When packets are captured on radio1 or radio2 interface and 
             promiscuous mode is enabled, the radio is changed to promiscuous
             mode. When capture stops, the promiscuous mode is disabled."
    ::= { apPacketCaptureConfig 2 }

apPktCaptureCfgClientFilterMode OBJECT-TYPE
    SYNTAX  INTEGER {
        enable(1), 
        disable(2)
    }
    MAX-ACCESS  read-write
    STATUS      current
    DESCRIPTION
            "Flag indicating whether or not WLAN client filter is enabled."
    ::= { apPacketCaptureConfig 3 }

apPktCaptureCfgClientFilterMacAddr OBJECT-TYPE
    SYNTAX  MacAddress
    MAX-ACCESS  read-write
    STATUS      current
    DESCRIPTION
            "MAC address of the client for which to capture data on the 802.11
	    interface."
    ::= { apPacketCaptureConfig 4 }

--*****************************************************************
--  apPacketCaptureFile       OBJECT IDENTIFIER ::= { apPacketCapture 3}
--*****************************************************************

apPktCaptureInterface OBJECT-TYPE
    SYNTAX      OCTET STRING (SIZE(3..32))
    MAX-ACCESS  read-write
    STATUS      current
    DESCRIPTION
            "The interface name on which to capture packets when using
	    file capture mode."
    ::= { apPacketCaptureFile 1 }

apPktCaptureTFTPServerIpType OBJECT-TYPE
    SYNTAX      InetAddressType
    MAX-ACCESS  read-only
    STATUS      current
    DESCRIPTION
            "The IP address type (IPv4 or IPv6) of the TFTP server."
    DEFVAL { ipv4 }
    ::= { apPacketCaptureFile 2 }

apPktCaptureTFTPServer OBJECT-TYPE
    SYNTAX      InetAddress
    MAX-ACCESS  read-write
    STATUS      current
    DESCRIPTION
            "The IPv4 or IPv6 address of the TFTP server to which the capture file
	    is downloaded."
    ::= { apPacketCaptureFile 3 }

apPktCaptureTFTPFilename OBJECT-TYPE
    SYNTAX      OCTET STRING (SIZE(0..128))
    MAX-ACCESS  read-write
    STATUS      current
    DESCRIPTION
            "The file name on the TFTP server to which the capture file
	    is downloaded. The file name includes the path."
    ::= { apPacketCaptureFile 4 }

apPacketCaptureFileDownloadAdminStart OBJECT-TYPE
    SYNTAX      INTEGER {
            none(1),
            start(2)
        }
    MAX-ACCESS  read-write 
    STATUS      current
    DESCRIPTION
            "Capture file download administrative start command.This is an action object.
             Setting this object to start begins packet capture file download to the target
	     and file specified by the TFTP Server and TFTP Filename fields. Download status
	     is reported in the Download Status field.Read on this object will always return none."
    ::= { apPacketCaptureFile 5 }

apPktCaptureDuration OBJECT-TYPE
    SYNTAX      INTEGER (10..3600)
    MAX-ACCESS  read-write
    STATUS      current
    DESCRIPTION
            "The number of seconds for which to capture packets into a file. Range
	    is from 10 to 3600 with a default value of 60. The capture is stopped
	    once the time limit is reached."
    DEFVAL { 60 }
    ::= { apPacketCaptureFile 6 }

apPktCaptureMaxFileSize OBJECT-TYPE
    SYNTAX      INTEGER (64..4096)
    MAX-ACCESS  read-write
    STATUS      current
    DESCRIPTION
            "The maximum capture file size. Range is from 64 to 4096 KB (kilobytes)
	    with a default value of 1024 (1MB). The capture is stopped once the
	    maximum file size is reached."
    DEFVAL { 1024 }
    ::= { apPacketCaptureFile 7 }

apPacketCaptureFileAdminStart OBJECT-TYPE
    SYNTAX      INTEGER {
            none(1),
            start(2)
        }
    MAX-ACCESS  read-write
    STATUS      current
    DESCRIPTION
            "File packet capture administrative start command.This is an action object.
	    Setting this object to start begins file packet capture.Read on this object will always return none."
    ::= { apPacketCaptureFile 8 }

--*****************************************************************
-- apPacketCaptureRemote      OBJECT IDENTIFIER ::= { apPacketCapture 4}
--*****************************************************************

apPktCaptureRemotePort OBJECT-TYPE
    SYNTAX      INTEGER(1025..65530)
    MAX-ACCESS  read-write
    STATUS      current
    DESCRIPTION
            "The lowest numbered IP port used for communicating with a remote
	    monitoring device. The system uses up to five consecutive port numbers
	    starting with the configured port. Valid range is 1025 to 65530 with a
	    default value of 2002."
    DEFVAL { 2002 }
    ::= { apPacketCaptureRemote 1 }

apPacketCaptureRemoteAdminStart OBJECT-TYPE
    SYNTAX      INTEGER {
            none(1),
	    start(2)
        }
    MAX-ACCESS  read-write 
    STATUS      current
    DESCRIPTION
            "Remote packet capture administrative start command.This is an action object.
	    Setting this object to start begins remote packet capture.Read on this object will always return none."
    ::= { apPacketCaptureRemote 2 }

--*****************************************************************
-- apDateTime                OBJECT IDENTIFIER ::= {ciscosbWLANAP 14}
--*****************************************************************

apSystemDateTime OBJECT-TYPE
    SYNTAX      DisplayString( SIZE (1..64) )
    MAX-ACCESS  read-write
    STATUS      current
    DESCRIPTION
            "System Date Month.Date.Year/Hour:Minute"
    ::= {apDateTime 1} 

--
--   apSystemTimeZoneTable
--
 apSystemTimeZoneTable OBJECT-TYPE
     SYNTAX       SEQUENCE OF ApSystemTimeZoneEntry
     MAX-ACCESS   not-accessible
     STATUS       current
     DESCRIPTION
       "This table represents the time zone list."
     ::= { apDateTime 2 }

 apSystemTimeZoneEntry OBJECT-TYPE
     SYNTAX       ApSystemTimeZoneEntry
     MAX-ACCESS   not-accessible
     STATUS       current
     DESCRIPTION
       "Each entry in this table represents a supported time zone."
     INDEX { apSystemTimeZoneIndex }
     ::= { apSystemTimeZoneTable 1 }

 ApSystemTimeZoneEntry ::=
     SEQUENCE {
         apSystemTimeZoneIndex      INTEGER,
         apSystemTimeZoneList           DisplayString
 }

 apSystemTimeZoneIndex OBJECT-TYPE
    SYNTAX      INTEGER (1..300)
    MAX-ACCESS  not-accessible
    STATUS      current
    DESCRIPTION
            "Time Zone index."
    ::= { apSystemTimeZoneEntry 1 }

 apSystemTimeZoneList OBJECT-TYPE
    SYNTAX      DisplayString( SIZE (1..64) )
    MAX-ACCESS  read-only
    STATUS      current
    DESCRIPTION
            "Time Zone List."
    ::= {apSystemTimeZoneEntry 2}

--
--   apSystemTimeZoneTable
--

apSystemTimeZone OBJECT-TYPE
    SYNTAX      DisplayString( SIZE (1..64) )
    MAX-ACCESS  read-write
    STATUS      current
    DESCRIPTION
            "Current System Time Zone."
    ::= {apDateTime 3 }

apSystemTimeDSTMode OBJECT-TYPE
    SYNTAX      INTEGER {
                on(1),
                off(2)
         }
    MAX-ACCESS  read-write
    STATUS      current
    DESCRIPTION
            "Daylight Time Saving(DST) Mode."
    DEFVAL {1}
    ::= {apDateTime 4 }

apSystemTimeDSTStart OBJECT-TYPE
    SYNTAX      DisplayString( SIZE (1..64) )
    MAX-ACCESS  read-write
    STATUS      current
    DESCRIPTION
            "DST Start Month.Week.Day/Hour:Minute"
    ::= {apDateTime 5 }

apSystemTimeDSTEnd OBJECT-TYPE
    SYNTAX      DisplayString( SIZE (1..64) ) 
    MAX-ACCESS  read-write
    STATUS      current
    DESCRIPTION
            "DST End Month.Week.Day/Hour:Minute"
    ::= {apDateTime 6 }

apSystemTimeDSTOffset OBJECT-TYPE
    SYNTAX      INTEGER {
                fifteen(15),
                thirty(30),
                forty-five(45),
                sixty(60),
                seventy-five(75),
                ninety(90),
                hundred-five(105),
                hundred-twenty(120)
    }
    MAX-ACCESS  read-write
    STATUS      current
    DESCRIPTION
            "Current System Time Zone."
    ::= {apDateTime 7}

--********************************************************************
-- apEmailAlert                OBJECT IDENTIFIER ::= {ciscosbWLANAP 16}
--********************************************************************
  apEmailAlertMode OBJECT-TYPE
        SYNTAX      INTEGER {
                    up(1),
                    down(2)
                    }
        MAX-ACCESS  read-write
        STATUS      current
        DESCRIPTION
        "To enable or disable email alerts feature."
        DEFVAL { down }
        ::= { apEmailAlertConfig 1 }

   apEmailAlertLogSeverity OBJECT-TYPE
        SYNTAX      ApLogSeverity
        MAX-ACCESS  read-write
        STATUS      current
        DESCRIPTION
            "The severity level of log messages that are buffered and 
             sent as email to the configured SMTP server."
        DEFVAL { warning }
        ::= { apEmailAlertConfig 2 }

   apEmailAlertUrgentSeverity OBJECT-TYPE
        SYNTAX      ApLogSeverity
        MAX-ACCESS  read-write
        STATUS      current
        DESCRIPTION
            "Th severity level for the log messages that are emailed 
            immediately to the configured SMPT server."
        DEFVAL { alert }
        ::= { apEmailAlertConfig 3 }
  
   apEmailAlertFromAddr OBJECT-TYPE
        SYNTAX      DisplayString
        MAX-ACCESS  read-write
        STATUS      current
        DESCRIPTION
            "Email Alert will send a email with this address as the from address."
        DEFVAL { NULL }
        ::= { apEmailAlertConfig 4 }

   apEmailAlertLogDuration OBJECT-TYPE
        SYNTAX      Unsigned32(30..1440)
        MAX-ACCESS  read-write
        STATUS      current
        DESCRIPTION
            "This duration in minutes determines how frequently the buffered
                log messages are sent to the SMTP server."
        DEFVAL { 30 }
        ::= { apEmailAlertConfig 5 }

   apEmailAlertSubject OBJECT-TYPE
        SYNTAX     DisplayString
        MAX-ACCESS read-write
        STATUS     current
        DESCRIPTION
           "The subject of the email that is sent by the email alert feature."
        ::= { apEmailAlertConfig 6 }

   apEmailAlertToAddr1 OBJECT-TYPE
        SYNTAX     DisplayString
        MAX-ACCESS read-write
        STATUS     current
        DESCRIPTION
           "The first To adderss is the destination email address of the 
           emails."
        DEFVAL { NULL }
        ::= { apEmailAlertConfig 7 }

   apEmailAlertToAddr2 OBJECT-TYPE
        SYNTAX     DisplayString
        MAX-ACCESS read-write
        STATUS     current
        DESCRIPTION
            "The second To adderss is the destination email address of the 
           emails."
        DEFVAL { NULL }
        ::= { apEmailAlertConfig 8 }

   apEmailAlertToAddr3 OBJECT-TYPE
        SYNTAX     DisplayString
        MAX-ACCESS read-write
        STATUS     current
        DESCRIPTION
             "The third To adderss is the destination email address of the 
           emails."
         DEFVAL { NULL }
        ::= { apEmailAlertConfig 9 }

    apEmailAlertServerAddress OBJECT-TYPE
        SYNTAX     InetAddress
        MAX-ACCESS read-write
        STATUS     current
        DESCRIPTION
           "The server address is of SMTP Server to send the email alert."
        DEFVAL { NULL }
        ::= { apEmailAlertConfig 10 }

    apEmailAlertServerAddressType        OBJECT-TYPE
        SYNTAX       InetAddressType
        MAX-ACCESS   read-only
        STATUS       current
        DESCRIPTION
          "Indicates the type of address being used for the
           SMTP server. Only IPv4 addresses and hostnames are allowed."
        DEFVAL { NULL }
        ::= { apEmailAlertConfig 11 }
    
    apEmailAlertServerSecurity OBJECT-TYPE
        SYNTAX     INTEGER {
                            open(1),
                            tlsv1(2)
                            }
        MAX-ACCESS read-write
        STATUS     current
        DESCRIPTION
           "The security option to be used to send Email alert messages."
        DEFVAL { open }
        ::= { apEmailAlertConfig 12 }

    apEmailAlertServerPort OBJECT-TYPE
        SYNTAX     Integer32(0..65535)
        MAX-ACCESS read-write
        STATUS     current
        DESCRIPTION
           "The server port of SMTP Server port."
        DEFVAL { 25 }
        ::= { apEmailAlertConfig 13 }

    apEmailAlertUserName OBJECT-TYPE
        SYNTAX      DisplayString
        MAX-ACCESS  read-write
        STATUS      current
        DESCRIPTION
           "The username used to authenitcate with SMTP seerver when 
            authentication is TLSv1. The maximum length is 64 characters."
        DEFVAL { NULL }
        ::= { apEmailAlertConfig 14 }

    apEmailAlertPassword OBJECT-TYPE
        SYNTAX      DisplayString( SIZE (1..64) )
        MAX-ACCESS read-write
        STATUS      current
        DESCRIPTION
            "This password used to authenticated with the SMTP server. 
            The maximum length is 64 characters."
        DEFVAL { NULL }
        ::= { apEmailAlertConfig 15 }

  apEmailAlertTestMail OBJECT-TYPE
        SYNTAX      INTEGER {
                    enable(1),
                    disable(2)
                    }
        MAX-ACCESS  write-only
        STATUS      current
        DESCRIPTION
        "Setting Test mail to enable triggers sending a test mail with the 
        configured SMTP server settings."
        DEFVAL { disable }
        ::= { apEmailAlertConfig 16 }

   apEmailAlertOperStatus OBJECT-TYPE
        SYNTAX      INTEGER{
                             up(1),
                             down(2)
                            }
        MAX-ACCESS read-only
        STATUS      current
        DESCRIPTION
            "The operational status of the email alert feature."
        DEFVAL { down }
        ::= { apEmailAlertStatus 1 }

   apEmailAlertFailedEmailCount OBJECT-TYPE
        SYNTAX      Counter32
        MAX-ACCESS read-only
        STATUS      current
        DESCRIPTION
            "The number of emails messages failed to be sent"
        DEFVAL { 0 }
        ::= { apEmailAlertStatus 2 }

   apEmailAlertSentEmailCount OBJECT-TYPE
        SYNTAX      Counter32
        MAX-ACCESS read-only
        STATUS      current
        DESCRIPTION
            "The number of emails messages successfully to be sent"
        DEFVAL { 0 }
        ::= { apEmailAlertStatus 3 }

   apEmailAlertTimeSinceLastEmailSent OBJECT-TYPE
        SYNTAX      DisplayString
        MAX-ACCESS read-only
        STATUS      current
        DESCRIPTION
            "The timestamp of email alert feature when the last email was sent."
        ::= { apEmailAlertStatus 4 }

   apEmailAlertTestMailStatus OBJECT-TYPE
        SYNTAX      INTEGER{
                            not-started(0),
                            started(1),
                            successfully-sent(2),
                            server-auth-failure(3)
                            }
        MAX-ACCESS read-only
        STATUS      current
        DESCRIPTION
            "The operational status of the last test-email action."
        DEFVAL { not-started }
        ::= { apEmailAlertStatus 5 }


--*********************************************************************
-- apScheduler                OBJECT IDENTIFIER ::= {ciscosbWLANAP 17}
--*********************************************************************

  apSchedulerMode OBJECT-TYPE
        SYNTAX      INTEGER {
                    up(1),
                    down(2)
                    }
        MAX-ACCESS  read-write
        STATUS      current
        DESCRIPTION
        "Configuration mode for AP scheduler."
        DEFVAL { down }
        ::= { apSchedulerConfig 1 }

  apSchedulerOperStatus OBJECT-TYPE
        SYNTAX      INTEGER{
                            up(1),
                            down(2)
                            }
        MAX-ACCESS read-only
        STATUS      current
        DESCRIPTION
            "The operational status of the AP scheduler."
        DEFVAL {down}
        ::= { apSchedulerConfig 2 }

  apSchedulerReasonCode OBJECT-TYPE
        SYNTAX   BITS {
                 status-up(0),
                 config-disabled(1),
                 time-not-set(2),
                 managed-mode(3)
                 }
        MAX-ACCESS      read-only
        STATUS          current
        DESCRIPTION
                "Defines the reason for the operational status of scheduler."
        ::= { apSchedulerConfig 3 }

--*****************************************************************
--                 apSchedulerProfileTable
--*****************************************************************

  apSchedulerProfileTable OBJECT-TYPE
        SYNTAX          SEQUENCE OF ApSchedulerProfileEntry
        MAX-ACCESS      not-accessible
        STATUS          current
        DESCRIPTION
        "The Scheduler Profile table for profile entries. Can configure 
         up to 16 Profiles and each profile is associated with a set of rules 
         defined in apSchedulerProfileRuleTable table."
        ::= { apSchedulerProfile 1 }

  apSchedulerProfileEntry  OBJECT-TYPE
        SYNTAX          ApSchedulerProfileEntry
        MAX-ACCESS      not-accessible
        STATUS          current
        DESCRIPTION
                "Entry in scheduler profile table."
    INDEX { apSchedulerProfileIndex, apSchedulerProfileName  }
    ::= { apSchedulerProfileTable 1 }

  ApSchedulerProfileEntry ::=
    SEQUENCE {
        apSchedulerProfileIndex                 INTEGER,
        apSchedulerProfileName                  DisplayString,     
        apSchedulerProfileRowStatus             RowStatus
        }

  apSchedulerProfileIndex  OBJECT-TYPE
        SYNTAX          INTEGER (1..16) 
        MAX-ACCESS      not-accessible
        STATUS          current
        DESCRIPTION
                "The Scheduler profile index."
        ::= { apSchedulerProfileEntry 1 }

  apSchedulerProfileName  OBJECT-TYPE
        SYNTAX          DisplayString(SIZE(0..32))
        MAX-ACCESS      not-accessible
        STATUS          current
        DESCRIPTION
                "The Scheduler profile name."
        ::= { apSchedulerProfileEntry 2 }

  apSchedulerProfileRowStatus OBJECT-TYPE
         SYNTAX      RowStatus
         MAX-ACCESS  read-create
         STATUS      current
         DESCRIPTION
                "Status of an entry. Supported values are:
                 - active (1)
                 - createAndGo (4)
                 - createAndWait (5)
                 - destroy (6)

         The administrator can only use createAndGo, createAndWait,
         and destroy. After creating an entry, its status is moved
         to active."
         ::= { apSchedulerProfileEntry 3 }

--*****************************************************************
--                 apSchedulerProfileRuleTable
--*****************************************************************
  apSchedulerProfileRuleTable OBJECT-TYPE
        SYNTAX          SEQUENCE OF ApSchedulerProfileRuleEntry
        MAX-ACCESS      not-accessible
        STATUS          current
        DESCRIPTION
        "The Scheduler Profile Rule table for rule entries. Can configure 
         up to 16 rules and each rule is associated with a profile  
         defined in apSchedulerProfileTable table."
        ::= { apSchedulerProfile 2 }

  apSchedulerProfileRuleEntry  OBJECT-TYPE
        SYNTAX          ApSchedulerProfileRuleEntry
        MAX-ACCESS      not-accessible
        STATUS          current
        DESCRIPTION
                "Entry in scheduler rule table."
    INDEX { apSchedulerProfileRuleIndex, apSchedulerProfileRuleNum }
    ::= { apSchedulerProfileRuleTable 1 }

  ApSchedulerProfileRuleEntry ::=
    SEQUENCE {
        apSchedulerProfileRuleIndex             INTEGER,
        apSchedulerProfileRuleNum               INTEGER,
        apSchedulerProfileDay                   INTEGER,
        apSchedulerStartTime                    DisplayString,
        apSchedulerEndTime                      DisplayString,
        apSchedulerProfileRuleRowStatus         RowStatus
        }

  apSchedulerProfileRuleIndex  OBJECT-TYPE
        SYNTAX          INTEGER (1..16) 
        MAX-ACCESS      not-accessible
        STATUS          current
        DESCRIPTION
                "The Scheduler profile index. This is reference to
                the apSchedulerProfileTable."
        ::= { apSchedulerProfileRuleEntry 1 }

  apSchedulerProfileRuleNum  OBJECT-TYPE
        SYNTAX          INTEGER (1..16)
        MAX-ACCESS      not-accessible
        STATUS          current
        DESCRIPTION
                "The Scheduler rule number. Index for this table."
        ::= { apSchedulerProfileRuleEntry 2 }
  apSchedulerProfileDay  OBJECT-TYPE
    SYNTAX      INTEGER {
                monday(1),
                tuesday(2),
                wednesday(3),
                thursday(4),
                friday(5),
                saturday(6),
                sunday(7),
                daily(8),
                weekday(9),
                weekend(10)
        }
        MAX-ACCESS      read-create
        STATUS          current
        DESCRIPTION
                "Defines the week of the day for the rule. The rule is applied 
                on the specified day (or days)."
        ::= { apSchedulerProfileRuleEntry 3 }

  apSchedulerStartTime OBJECT-TYPE
      SYNTAX      DisplayString( SIZE (1..64) )
      MAX-ACCESS  read-create
      STATUS      current
      DESCRIPTION
              "Defines the start time of the rule. The format is HH:MM with 
              hour between 0 to 24 and minute between 0 to 59."
      ::= {apSchedulerProfileRuleEntry 4 }
  apSchedulerEndTime OBJECT-TYPE
      SYNTAX      DisplayString( SIZE (1..64) )
      MAX-ACCESS  read-create
      STATUS      current
      DESCRIPTION
              "Defines the end time of the rule. The format is HH:MM with 
              hour between 0 to 24 and minute between 0 to 59."
      ::= {apSchedulerProfileRuleEntry 5 }

  apSchedulerProfileRuleRowStatus OBJECT-TYPE
         SYNTAX      RowStatus
         MAX-ACCESS  read-create
         STATUS      current
         DESCRIPTION
                "Status of an entry. Supported values are:
                 - active (1)
                 - createAndGo (4)
                 - createAndWait (5)
                 - destroy (6)

         The administrator can only use createAndGo, createAndWait,
         and destroy. After creating an entry, its status is moved
         to active."
         ::= { apSchedulerProfileRuleEntry 6 }
--*****************************************************************
-- apWPSGlobal  OBJECT-IDENTIFIER ::= { apWPS 1 }
--*****************************************************************

  apWPSGenerateDevicePIN OBJECT-TYPE
        SYNTAX      INTEGER {
                    disable(0),
                    enable(1)
                    }
        MAX-ACCESS  write-only
        STATUS      current
        DESCRIPTION
        "Setting this object to enable triggers generating device PIN."
        DEFVAL { disable }
        ::= { apWPSGlobal 1}

  apWPSDevicePIN OBJECT-TYPE
        SYNTAX      DisplayString( SIZE (1..8) )
        MAX-ACCESS  read-only
        STATUS      current
        DESCRIPTION
        "WPS device PIN."
        ::= { apWPSGlobal 2}

  apWPSDeviceName OBJECT-TYPE
        SYNTAX      DisplayString
        MAX-ACCESS  read-write
        STATUS      current
        DESCRIPTION
           "A meaningful name that users use to identify this device. 
            The maximum length is 32 characters."
        ::= { apWPSGlobal 3 }

  apWPSProtocolVersion OBJECT-TYPE
        SYNTAX      DisplayString
        MAX-ACCESS  read-only
        STATUS      current
        DESCRIPTION
        "WPS Protocol Version."
        DEFVAL { "2.0" }
        ::= { apWPSGlobal 4}

  apWPSGlobalOperStatus OBJECT-TYPE
        SYNTAX      INTEGER {
                    disable(0),
                    enable(1)
                    }
        MAX-ACCESS  read-only
        STATUS      current
        DESCRIPTION
        "WPS Global Operational Status."
        DEFVAL { disable }
        ::= { apWPSGlobal 5} 

--*****************************************************************
-- apWPSInstanceTable  OBJECT-IDENTIFIER ::= { apWPS 2 }
--*****************************************************************

 apWPSInstanceTable OBJECT-TYPE
    SYNTAX      SEQUENCE OF ApWPSInstanceEntry
    MAX-ACCESS  not-accessible
    STATUS      current
    DESCRIPTION
            "A list of WPS configuration entries."
    ::= { apWPS 2 }

 apWPSInstanceEntry OBJECT-TYPE
    SYNTAX      ApWPSInstanceEntry
    MAX-ACCESS  not-accessible
    STATUS      current
    DESCRIPTION
            "An entry containing WPS configuration information applicable
             to the AP."
    INDEX   { apWPSInstanceIndex }
    ::= { apWPSInstanceTable 1 }

  ApWPSInstanceEntry ::=
    SEQUENCE {
        apWPSInstanceIndex          Integer32,
        apWPSMode                   INTEGER,
        apWPSInstanceRadio          INTEGER,
        apWPSInstanceVap            Integer32,
        apWPSBuiltInRegistrar       INTEGER,
        apWPSReportedConfigState    INTEGER,
        apWPSEnrollmentPin          DisplayString,
        apWPSEnrollmentPbc          INTEGER,
        apWPSStatus                 INTEGER,
        apWPSStatusReasonCode       BITS,
        apWPSTransactionStatus      INTEGER,
        apWPSOperStatus             INTEGER,
        apWPSApLockdownStatus       INTEGER,
        apWPSApPinFailedAttempts   INTEGER,
        apWPSApLockdownDuration    INTEGER,
        apWPSApLockdownTimeStamp   DisplayString
  }

  apWPSInstanceIndex OBJECT-TYPE
        SYNTAX      Integer32(1..1)
        MAX-ACCESS  not-accessible
        STATUS      current
        DESCRIPTION
        "Index of the apWPSInstanceTable."
        ::= { apWPSInstanceEntry 1}

  apWPSMode OBJECT-TYPE
        SYNTAX      INTEGER {
                    disable(0),
                    enable(1)
                    }
        MAX-ACCESS  read-write
        STATUS      current
        DESCRIPTION
        "This command enables or disables the WPS Cofiguration for a given instance."
        DEFVAL { enable }
        ::= { apWPSInstanceEntry 2}

  apWPSInstanceRadio OBJECT-TYPE
        SYNTAX      INTEGER {
              wlan0(1),
              wlan1(2)
                    }
        MAX-ACCESS  read-write
        STATUS      current
        DESCRIPTION
            "This command enables or disables the WPS Cofiguration for a given radio."
        DEFVAL { wlan0 }
        ::= { apWPSInstanceEntry 3 }

  apWPSInstanceVap OBJECT-TYPE
        SYNTAX      Integer32
        MAX-ACCESS  read-write
        STATUS      current
        DESCRIPTION
        "This command enables or disables the WPS Cofiguration for a given VAP."
        DEFVAL {0}
        ::= { apWPSInstanceEntry 4}

  apWPSBuiltInRegistrar OBJECT-TYPE
        SYNTAX      INTEGER {
                    disable(0),
                    enable(1)
                    }
        MAX-ACCESS  read-write
        STATUS      current
        DESCRIPTION
        "This command enables or disables the WPS internal registrar for a given instance."
        DEFVAL { enable }
        ::= { apWPSInstanceEntry 5}

  apWPSReportedConfigState OBJECT-TYPE
        SYNTAX      INTEGER {
                    disable(0),
                    enable(1)
                    }
        MAX-ACCESS  read-write
        STATUS      current
        DESCRIPTION
        "This command enables or disables the WPS Config State for a given instance. 
         An unconfigured VAP implies that there is some external registrar in the network."
        DEFVAL { disable }
        ::= { apWPSInstanceEntry 6}

  apWPSEnrollmentPin OBJECT-TYPE
        SYNTAX      DisplayString( SIZE (1..8) )
        MAX-ACCESS  write-only
        STATUS      current
        DESCRIPTION
            "Administrative command for starting and stopping the enrollment process using pin.This is an action object.
             Setting this object to a valid pin begins the enrollment process. Setting this object to stop, stops the 
             enrollment process.Enrollment status is reported in the WPS Transaction Status field."
        DEFVAL { "none" }
        ::= { apWPSInstanceEntry 7 }

  apWPSEnrollmentPbc OBJECT-TYPE
        SYNTAX      INTEGER {
            none(0),
            stop(1),
            start(2)
        }
        MAX-ACCESS  write-only
        STATUS      current
        DESCRIPTION
            "Administrative command for starting and stopping the enrollment process using pbc method.
             This is an action object. Enrollment status is reported in the WPS Transaction  Status field."
        DEFVAL { none }
        ::= { apWPSInstanceEntry 8 }

  apWPSStatus OBJECT-TYPE
        SYNTAX      INTEGER {
                    disabled(0),
                    enabled(1)
                    }
        MAX-ACCESS  read-only
        STATUS      current
        DESCRIPTION
        "This command returns the current operational status of WPS."
        ::= { apWPSInstanceEntry 9}

  apWPSStatusReasonCode OBJECT-TYPE
        SYNTAX   BITS {
                 enabled(0),
                 wps-disabled(1),
                 vap-disabled(2),
                 non-broadcast-ssid(3),
                 incompatible-vap-security-config(4),
                 mac-filter-enabled(5),
                 managed-ap(6)
                 }
        MAX-ACCESS      read-only
        STATUS          current
        DESCRIPTION
        "Defines the reason code for WPS operational status."
        ::= { apWPSInstanceEntry 10 }

  apWPSTransactionStatus OBJECT-TYPE
        SYNTAX      INTEGER {
                    none(0),
                    success(1),
                    wps-msg-error(2),
                    timed-out(3),
                    in-progress(4)
                    }
        MAX-ACCESS  read-only
        STATUS      current
        DESCRIPTION
        "This command returns the last WPS enrollment status."
        DEFVAL { none }
        ::= { apWPSInstanceEntry 11}

  apWPSOperStatus OBJECT-TYPE
        SYNTAX      INTEGER {
                    disabled(1),
                    ready(2),
                    configuring(3),
                    adding-enrollee(4),
                    registering(5)
                    }
        MAX-ACCESS  read-only
        STATUS      current
        DESCRIPTION
        "This command returns the current operational status of WPS instance."        
        ::= { apWPSInstanceEntry 12}

  apWPSApLockdownStatus OBJECT-TYPE
        SYNTAX      INTEGER {
                    disabled(1),
                    temp-locked(2),
                    perm-locked(3)
                    }
        MAX-ACCESS  read-only
        STATUS      current
        DESCRIPTION
                "Indicates AP lock down status. When the AP is locked down, essentially the external registrar (PIN-ER) configuration mode is
                disabled so that no ER can be authenticated. After 2 unsuccessful attempts with invalid AP PIN, for every consecutive failed attempt
                the AP is locked temporarily. When the max count reaches, the AP is locked down permanently. Once AP is locked permanently,
                reboot the device to unlock the AP."
        DEFVAL {1}
        ::= { apWPSInstanceEntry 13 }
  
  apWPSApPinFailedAttempts OBJECT-TYPE
        SYNTAX      INTEGER
        MAX-ACCESS  read-only
        STATUS      current
        DESCRIPTION
        "Indicates the number of consecutive failed attempts to authenticate any external registrar. After 10 failed attempts the external registrar (PIN-ER)
        configuration mode is disabled ( AP is locked down) permanently. The count is reset when the AP lockdown is reset by rebooting the AP."
        DEFVAL {0}
        ::= { apWPSInstanceEntry 14}

  apWPSApLockdownDuration OBJECT-TYPE
        SYNTAX      INTEGER
        MAX-ACCESS  read-only
        STATUS      current
        DESCRIPTION
       	"If AP is in lockdown state (or external registrar (PIN-ER) configuration mode is disabled) temporarily, this MIB value indicates duration in minues for the lockdown.
       	If AP is not locked, duration is 0. If AP is locked permanently, duration is -1."
        DEFVAL {0}
        ::= { apWPSInstanceEntry 15}

  apWPSApLockdownTimeStamp OBJECT-TYPE
        SYNTAX      DisplayString( SIZE (1..64) )
        MAX-ACCESS  read-only
        STATUS      current
        DESCRIPTION
        "If AP is in lockdown state (or external registrar (PIN-ER) configuration mode is disabled), this MIB value indicates the time when the AP was locked down."
        DEFVAL {0}
        ::= { apWPSInstanceEntry 16}

--*****************************************************************
--  apWPSApLockdownTrap         OBJECT IDENTIFIER ::= { apWPS 3 }
--*****************************************************************
apWPSApLockdownTrap        OBJECT IDENTIFIER
                ::= { apWPS 3}

apWPSApLockdownTrapPrefix       OBJECT IDENTIFIER
                ::= { apWPSApLockdownTrap 0 }

apWPSApLockdownTrapObjects      OBJECT IDENTIFIER
                ::= { apWPSApLockdownTrap 1 }

apWPSApLockdownTrapSeverity     OBJECT-TYPE
SYNTAX          SnmpAdminString
MAX-ACCESS      accessible-for-notify
STATUS          current
DESCRIPTION     "This string contains severity of trap message."
::= {apWPSApLockdownTrapObjects 1 }

apWPSApLockdownTrapMessage      OBJECT-TYPE
SYNTAX          SnmpAdminString
MAX-ACCESS      accessible-for-notify
STATUS          current
DESCRIPTION     "This string contains contents of trap message."
::= { apWPSApLockdownTrapObjects        2 }

apWPSApLockdownTrapLockedTs   OBJECT-TYPE
SYNTAX          SnmpAdminString
MAX-ACCESS      accessible-for-notify
STATUS          current
DESCRIPTION     "This string contains the time stamp (ts) when AP was locked."
::= { apWPSApLockdownTrapObjects        3 }

apWPSApLockdownTrapLockedDuration       OBJECT-TYPE
SYNTAX          SnmpAdminString
MAX-ACCESS      accessible-for-notify
STATUS          current
DESCRIPTION     "This string contains the duration for which the ER config mode is disabled or the AP is locked down."
::= { apWPSApLockdownTrapObjects        4}

apWPSApLockdownTrapFailedAttempts       OBJECT-TYPE
SYNTAX          SnmpAdminString
MAX-ACCESS      accessible-for-notify
STATUS          current
DESCRIPTION     "This string contains the number of attempts that failed to authenticate an ER due to invalid PIN ."
::= { apWPSApLockdownTrapObjects        5}

apWPSApLockdownTrapNotification NOTIFICATION-TYPE
OBJECTS         { apWPSApLockdownTrapSeverity,
                        apWPSApLockdownTrapMessage,
                        apWPSApLockdownTrapLockedTs,
                        apWPSApLockdownTrapLockedDuration,
                        apWPSApLockdownTrapFailedAttempts}
STATUS          current
DESCRIPTION     "Object which contains information about the WPSApLockdown client."
::= { apWPSApLockdownTrapPrefix 1 }


--*****************************************************************
--      apWgBridgeEntry      OBJECT IDENTIFIER ::= { apWgBridge 1 }                            
--*****************************************************************

apWgBridgeRadioName OBJECT-TYPE
    SYNTAX      DisplayString
    MAX-ACCESS  read-write
    STATUS      current
    DESCRIPTION
            "AP radio name."
    ::= { apWgBridgeEntry 1 }


apWgBridgeMode  OBJECT-TYPE
        SYNTAX INTEGER
               {
                 up(1),
                 down(2)
               }
        MAX-ACCESS read-write
        STATUS current
        DESCRIPTION
                "Mode to enable AP to operate in Bridge Mode.  If the value is up,  AP will operate in
                 Bridge Mode; Otherwise,  the AP will operate in the normal default mode."
        DEFVAL      { down }
        ::= { apWgBridgeEntry 2}


--*****************************************************************
--  apWgBridgeUpstrmEntry     OBJECT IDENTIFIER ::= { apWgBridge 2 }
--*****************************************************************

apWgBridgeUpstrmName           OBJECT-TYPE
        SYNTAX           DisplayString
        MAX-ACCESS       read-only
        STATUS           current
        DESCRIPTION
        	"Indicates name of interface."
        ::= { apWgBridgeUpstrmEntry 1 }


apWgBridgeUpstrmBSSID     OBJECT-TYPE
        SYNTAX           MacAddress
        MAX-ACCESS       read-write
        STATUS           current
        DESCRIPTION
		"Indicates the Upstream BSSID."
        ::= { apWgBridgeUpstrmEntry 2 }

apWgBridgeUpstrmSsid OBJECT-TYPE
    SYNTAX      ApSsid
    MAX-ACCESS  read-write
    STATUS      current
    DESCRIPTION
	"Indicates the upstream SSID, which must consist of 1 to 32
        alphanumeric characters and uniquely identify this upstream SSID."
    ::= { apWgBridgeUpstrmEntry 3 }

apWgBridgeUpstrmSecurity OBJECT-TYPE
    SYNTAX      INTEGER{
                        plainText(1),
                        staticWep(2),
                        wpaPersonal(3),
                        wpaEnterprise(4)
                }
    MAX-ACCESS  read-write
    STATUS      current
    DESCRIPTION
        "Indicates security to use to connect to the upstream AP."
    DEFVAL      { plainText }        
    ::= { apWgBridgeUpstrmEntry 4 }

apWgBridgeUpstrmWpaPersonalKey OBJECT-TYPE
    SYNTAX      DisplayString(SIZE(8..63))
    MAX-ACCESS  read-write
    STATUS      current
    DESCRIPTION
        "Pre-shared key for Wireless Protected Access (WPA) personal.
        Only used when security is wpa-personal.  Valid value is an
        ASCII string between 8 and 63 characters."
    ::= { apWgBridgeUpstrmEntry 5 }

apWgBridgeUpstrmWepKeyAscii OBJECT-TYPE
    SYNTAX      TruthValue
    MAX-ACCESS  read-write
    STATUS      current
    DESCRIPTION
        "Indicates whether or not the Wired Equivalent Privacy (WEP)
         Key is in ASCII or HEX."
    DEFVAL         { false }
    ::= { apWgBridgeUpstrmEntry 6 }

apWgBridgeUpstrmWepKeyLength OBJECT-TYPE
    SYNTAX      INTEGER{
                forty(40),
                onehundredfour(104)
                }
    MAX-ACCESS  read-write
    STATUS      current
    DESCRIPTION
        "Length of the WEP key.
        The key length values used by the SNMP do not include the
        initialization vector in the length. On the web UI,
        longer key length values may be shown which include the 24-bit 
        initialization vector. For example, a key length of 40 bits
        (not including initialization vector) is equivalent to a
        key length of 64 bits (with initialization vector)."
    DEFVAL      { onehundredfour }        
    ::= { apWgBridgeUpstrmEntry 7 }

apWgBridgeUpstrmWepDefaultKey OBJECT-TYPE
    SYNTAX      Integer32(1..4)
    MAX-ACCESS  read-write
    STATUS      current
    DESCRIPTION
	"Indicates the WEP key index to use when transmitting. 
        Only used when security is static-wep. Valid value is a number
        between 1 and 4."
    DEFVAL {1}          
    ::= { apWgBridgeUpstrmEntry 8 }

apWgBridgeUpstrmWepKey1 OBJECT-TYPE
    SYNTAX      DisplayString
    MAX-ACCESS  read-write
    STATUS      current
    DESCRIPTION
        "Configure WEP key 1. The number of
        characters required for each WEP key depends on how user sets
        'Key Length' and 'Key Type':

        - If Key Length is 40 bits and the Key Type is 'ASCII',
          then each WEP key must be 5 characters long.
        - If Key Length is 40 bits and Key Type is 'Hex',
          then each WEP key must be 10 characters long.
        - If Key Length is 104 bits and Key Type is 'ASCII',
          then each WEP Key must be 13 characters long.
        - If Key Length is 104 bits and Key Type is 'Hex',
          then each WEP Key must be 26 characters long."
    ::= { apWgBridgeUpstrmEntry 9 }

apWgBridgeUpstrmWepKey2 OBJECT-TYPE
    SYNTAX      DisplayString
    MAX-ACCESS  read-write
    STATUS      current
    DESCRIPTION
        "Configure WEP key 2. The number of
        characters required for each WEP key depends on how user sets
        'Key Length' and 'Key Type':

        - If Key Length is 40 bits and the Key Type is 'ASCII',
          then each WEP key must be 5 characters long.
        - If Key Length is 40 bits and Key Type is 'Hex',
          then each WEP key must be 10 characters long.
        - If Key Length is 104 bits and Key Type is 'ASCII',
          then each WEP Key must be 13 characters long.
        - If Key Length is 104 bits and Key Type is 'Hex',
          then each WEP Key must be 26 characters long."
    ::= { apWgBridgeUpstrmEntry 10 }

apWgBridgeUpstrmWepKey3 OBJECT-TYPE
    SYNTAX      DisplayString
    MAX-ACCESS  read-write
    STATUS      current
    DESCRIPTION
        "Configure WEP key 3. The number of
        characters required for each WEP key depends on how user sets
        'Key Length' and 'Key Type':

        - If Key Length is 40 bits and the Key Type is 'ASCII',
          then each WEP key must be 5 characters long.
        - If Key Length is 40 bits and Key Type is 'Hex',
          then each WEP key must be 10 characters long.
        - If Key Length is 104 bits and Key Type is 'ASCII',
          then each WEP Key must be 13 characters long.
        - If Key Length is 104 bits and Key Type is 'Hex',
          then each WEP Key must be 26 characters long."
    ::= { apWgBridgeUpstrmEntry 11 }

apWgBridgeUpstrmWepKey4 OBJECT-TYPE
    SYNTAX      DisplayString
    MAX-ACCESS  read-write
    STATUS      current
    DESCRIPTION
        "Configure WEP key 4. The number of
        characters required for each WEP key depends on how user sets
        'Key Length' and 'Key Type':

        - If Key Length is 40 bits and the Key Type is 'ASCII',
          then each WEP key must be 5 characters long.
        - If Key Length is 40 bits and Key Type is 'Hex',
          then each WEP key must be 10 characters long.
        - If Key Length is 104 bits and Key Type is 'ASCII',
          then each WEP Key must be 13 characters long.
        - If Key Length is 104 bits and Key Type is 'Hex',
          then each WEP Key must be 26 characters long."
    ::= { apWgBridgeUpstrmEntry 12 }


apWgBridgeUpstrmOpenSystemAuth OBJECT-TYPE
    SYNTAX      TruthValue
    MAX-ACCESS  read-write
    STATUS      current
    DESCRIPTION
        "Indicates whether Open System authentication is permitted.
	Only used when security is static-wep."
    DEFVAL      { true }        
    ::= { apWgBridgeUpstrmEntry 13 }

apWgBridgeUpstrmSharedKeyAuth OBJECT-TYPE
    SYNTAX      TruthValue
    MAX-ACCESS  read-write
    STATUS      current
    DESCRIPTION
        "Indicates whether Shared Key authentication is permitted.
	Only used when security is static-wep."

    DEFVAL      { false }        
    ::= { apWgBridgeUpstrmEntry 14 }


apWgBridgeUpstrmWpaAllowed OBJECT-TYPE
    SYNTAX      TruthValue
    MAX-ACCESS  read-write
    STATUS      current
    DESCRIPTION
        "Indicates whether WPA is allowed.
         apWgBridgeUpstrmWpa2Allowed must be set to 'true'
         to turn off WPA (false)." 
    DEFVAL      { true }        
    ::= { apWgBridgeUpstrmEntry 15 }

apWgBridgeUpstrmWpa2Allowed OBJECT-TYPE
    SYNTAX      TruthValue
    MAX-ACCESS  read-write
    STATUS      current
    DESCRIPTION
        "Indicates whether WPA2 is allowed.
         apWgBridgeUpstrmWpaAllowed must be set to 'true'
         to turn off WPA2(false)."
    DEFVAL      { true }        
    ::= { apWgBridgeUpstrmEntry 16 }

apWgBridgeUpstrmVlanID	    OBJECT-TYPE
        SYNTAX          Integer32 (1..4094)
        MAX-ACCESS      read-write
        STATUS          current
        DESCRIPTION
                "VLAN ID associated with VAP."
        DEFVAL    { 1 }               
        ::= { apWgBridgeUpstrmEntry 17 }

apWgBridgeUpstrmConnStatus OBJECT-TYPE
    SYNTAX      DisplayString
    MAX-ACCESS  read-only
    STATUS      current
    DESCRIPTION
        "Conection Status of the Upstream Interface."
    ::= { apWgBridgeUpstrmEntry 18 }

apWgBridgeUpstrmRxBytes        OBJECT-TYPE
        SYNTAX           Integer32
        MAX-ACCESS       read-only
        STATUS           current
        DESCRIPTION
             "Indicates received bytes."
        ::= { apWgBridgeUpstrmEntry 19 }       

apWgBridgeUpstrmRxPackets      OBJECT-TYPE
        SYNTAX           Integer32
        MAX-ACCESS       read-only
        STATUS           current
        DESCRIPTION
        "Indicates received packets."
        ::= { apWgBridgeUpstrmEntry 20 } 

apWgBridgeUpstrmTxBytes        OBJECT-TYPE
        SYNTAX           Integer32
        MAX-ACCESS       read-only
        STATUS           current
        DESCRIPTION
             "Indicates transmitted bytes."
        ::= { apWgBridgeUpstrmEntry 21 }       

apWgBridgeUpstrmTxPackets      OBJECT-TYPE
        SYNTAX           Integer32
        MAX-ACCESS       read-only
        STATUS           current
        DESCRIPTION
             "Indicates transmitted packets."
        ::= { apWgBridgeUpstrmEntry 22 }

apWgBridgeUpstrmConfigUser OBJECT-TYPE
    SYNTAX  DisplayString (SIZE (1..64))
    MAX-ACCESS  read-write
    STATUS  current
    DESCRIPTION
        "Indicates the user name/identity used for WPA supplicant
        authentication.  ASCII printable characters are allowed,
        which includes upper and lower case alphabetic letters,
        numeric digits, and special symbols such as @ and #
        except leading and trailing Spaces."
    ::= { apWgBridgeUpstrmEntry 23 }

apWgBridgeUpstrmConfigPassword OBJECT-TYPE
    SYNTAX  DisplayString( SIZE (1..64) )
    MAX-ACCESS  read-write
    STATUS  current
    DESCRIPTION
        "Configure the password used for WPA supplicant
        authentication.  If apWgBridgeUpstrmConfigEapMethod is set
        to peap, this value is the user's password.  If
        apWgBridgeUpstrmConfigEapMethod is set to tls, this value is the
        private key password.  ASCII printable characters are allowed,
        which includes upper and lower case alphabetic letters,
        numeric digits, and special symbols such as @ and #
        except leading and trailing Spaces.
        The read of this parameter will return null string."
    ::= { apWgBridgeUpstrmEntry 24 }

apWgBridgeUpstrmConfigEapMethod OBJECT-TYPE
    SYNTAX  INTEGER {
                peap(1),
                tls(2)
            }
    MAX-ACCESS  read-write
    STATUS  current
    DESCRIPTION
        "Configure the EAP Method used for WPA supplicant
        authentication."
    DEFVAL { peap }
    ::= { apWgBridgeUpstrmEntry 25 }

apWgBridgeUpstrmCertificateFilePresent OBJECT-TYPE
    SYNTAX  INTEGER {
                yes(1),
                no(2)
            }
    MAX-ACCESS  read-only
    STATUS  current
    DESCRIPTION
        "Inidicates whether the TLS certificate file is present
        for use with WPA supplicant authentication."
    ::= { apWgBridgeUpstrmEntry 26 }

apWgBridgeUpstrmCertificateFileExpirationDate OBJECT-TYPE
    SYNTAX  DisplayString
    MAX-ACCESS  read-only
    STATUS  current
    DESCRIPTION
        "The expiration date of the TLS certificate"
    ::= { apWgBridgeUpstrmEntry 27 }

apWgBridgeUpstrmCertificateTFTPServerAddressType OBJECT-TYPE
    SYNTAX  InetAddressType
    MAX-ACCESS  read-only
    STATUS  current
    DESCRIPTION
            "Type of the IP address as defined in the InetAddress MIB.
             This is the address type of the TFTP server."
    REFERENCE "RFC 3291"
    DEFVAL { unknown }
    ::= { apWgBridgeUpstrmEntry 28 }

apWgBridgeUpstrmCertificateTFTPServerAddress OBJECT-TYPE
    SYNTAX  InetAddress
    MAX-ACCESS  read-write
    STATUS  current
    DESCRIPTION
            "The address of the TFTP Server from which to get the
             certificate file."
    ::= { apWgBridgeUpstrmEntry 29 }

apWgBridgeUpstrmCertificateTFTPServerPort OBJECT-TYPE
    SYNTAX  Integer32(1..65535)
    MAX-ACCESS  read-write
    STATUS  current
    DESCRIPTION
            "The port on the TFTP Server from which to get the
             certificate file."
    DEFVAL { 69 }
    ::= { apWgBridgeUpstrmEntry 30 }

apWgBridgeUpstrmCertificateUploadDirectory OBJECT-TYPE
    SYNTAX  DisplayString (SIZE (0..255))
    MAX-ACCESS  read-write
    STATUS  current
    DESCRIPTION
            "Directory on the server from which to get the certificate
             file.  This directory name does not contain the filename."
    ::= { apWgBridgeUpstrmEntry 31}

apWgBridgeUpstrmCertificateUploadFilename OBJECT-TYPE
    SYNTAX  DisplayString (SIZE (0..64))
    MAX-ACCESS  read-write
    STATUS  current
    DESCRIPTION
            "File name on the server of the certificate file."
    ::= { apWgBridgeUpstrmEntry 32 }

apWgBridgeUpstrmCertificateUploadProtocol OBJECT-TYPE
    SYNTAX INTEGER {
        tftp(1)
    }
    MAX-ACCESS  read-only
    STATUS  current
    DESCRIPTION
            "The protocol used for uploading the certificate file."
    DEFVAL { tftp }
    ::= { apWgBridgeUpstrmEntry 33}

apWgBridgeUpstrmCertificateUploadStart OBJECT-TYPE
    SYNTAX INTEGER {
        enable(1),
        disable(2)
    }
    MAX-ACCESS  read-write
    STATUS  current
    DESCRIPTION
            "This object initiates the certificate file upload to the AP."
    DEFVAL { disable }
    ::= { apWgBridgeUpstrmEntry 34 }

apWgBridgeUpstrmCertificateUploadStatus OBJECT-TYPE
    SYNTAX INTEGER {
        notStarted(1),
        inProgress(2),
        success(3),
        failed(4)
    }
    MAX-ACCESS  read-only
    STATUS  current
    DESCRIPTION
            "The upload status of the certificate file to the AP."
    DEFVAL { notStarted }
    ::= { apWgBridgeUpstrmEntry 35 }
 
--*****************************************************************
--  apWgBridgeDwstrmEntry     OBJECT IDENTIFIER ::= { apWgBridge 3 }
--*****************************************************************
apWgBridgeDwstrmName           OBJECT-TYPE
        SYNTAX           DisplayString
        MAX-ACCESS       read-only
        STATUS           current
        DESCRIPTION
             "Indicates name of interface."
        ::= { apWgBridgeDwstrmEntry 1 }


apWgBridgeDwstrmSsid OBJECT-TYPE
    SYNTAX      ApSsid
    MAX-ACCESS  read-write
    STATUS      current
    DESCRIPTION
	"Indicates the downstream SSID, which must consist of 1 to 32
        alphanumeric characters and uniquely identify this downstream SSID."
    ::= { apWgBridgeDwstrmEntry 2 }

apWgBridgeDwstrmSecurity OBJECT-TYPE
    SYNTAX      INTEGER{
                        plainText(1),
                        staticWep(2),
                        wpaPersonal(3)
                }
    MAX-ACCESS  read-write
    STATUS      current
    DESCRIPTION
        "Indicates security to use for downstream interface."
    DEFVAL      { plainText }        
    ::= { apWgBridgeDwstrmEntry 3 }

apWgBridgeDwstrmWpaPersonalKey OBJECT-TYPE
    SYNTAX      DisplayString(SIZE(8..63))
    MAX-ACCESS  read-write
    STATUS      current
    DESCRIPTION
        "Pre-shared key for Wireless Protected Access (WPA) personal.
        Only used when security is wpa-personal. Valid value is an
        ASCII string between 8 and 63 characters."
    ::= { apWgBridgeDwstrmEntry 4 }

apWgBridgeDwstrmWepKeyAscii OBJECT-TYPE
    SYNTAX      TruthValue
    MAX-ACCESS  read-write
    STATUS      current
    DESCRIPTION
        "Indicates whether or not the Wired Equivalent Privacy (WEP)
         Key is in ASCII or HEX."
    DEFVAL         { false }
    ::= { apWgBridgeDwstrmEntry 5 }

apWgBridgeDwstrmWepKeyLength OBJECT-TYPE
    SYNTAX      INTEGER{
                forty(40),
                onehundredfour(104)
                }
    MAX-ACCESS  read-write
    STATUS      current
    DESCRIPTION
        "Length of the WEP key.
        The key length values used by the SNMP do not include the
        initialization vector in the length. On the web UI,
        longer key length values may be shown which include the 24-bit 
        initialization vector. For example, a key length of 40 bits
        (not including initialization vector) is equivalent to a
        key length of 64 bits (with initialization vector)."
    DEFVAL      { onehundredfour }        
    ::= { apWgBridgeDwstrmEntry 6 }

apWgBridgeDwstrmWepDefaultKey OBJECT-TYPE
    SYNTAX      Integer32(1..4)
    MAX-ACCESS  read-write
    STATUS      current
    DESCRIPTION
            "Indicates the WEP key index to use when transmitting. 
        Only used when security is static-wep. Valid value is a number
        between 1 and 4."
    DEFVAL {1}          
    ::= { apWgBridgeDwstrmEntry 7 }

apWgBridgeDwstrmWepKey1 OBJECT-TYPE
    SYNTAX      DisplayString
    MAX-ACCESS  read-write
    STATUS      current
    DESCRIPTION
        "Configure WEP key 1. The number of
        characters required for each WEP key depends on how user sets
        'Key Length' and 'Key Type':

        - If Key Length is 40 bits and the Key Type is 'ASCII',
          then each WEP key must be 5 characters long.
        - If Key Length is 40 bits and Key Type is 'Hex',
          then each WEP key must be 10 characters long.
        - If Key Length is 104 bits and Key Type is 'ASCII',
          then each WEP Key must be 13 characters long.
        - If Key Length is 104 bits and Key Type is 'Hex',
          then each WEP Key must be 26 characters long."
    ::= { apWgBridgeDwstrmEntry 8 }

apWgBridgeDwstrmWepKey2 OBJECT-TYPE
    SYNTAX      DisplayString
    MAX-ACCESS  read-write
    STATUS      current
    DESCRIPTION
        "Configure WEP key 2. The number of
        characters required for each WEP key depends on how user sets
        'Key Length' and 'Key Type':

        - If Key Length is 40 bits and the Key Type is 'ASCII',
          then each WEP key must be 5 characters long.
        - If Key Length is 40 bits and Key Type is 'Hex',
          then each WEP key must be 10 characters long.
        - If Key Length is 104 bits and Key Type is 'ASCII',
          then each WEP Key must be 13 characters long.
        - If Key Length is 104 bits and Key Type is 'Hex',
          then each WEP Key must be 26 characters long."
    ::= { apWgBridgeDwstrmEntry 9 }

apWgBridgeDwstrmWepKey3 OBJECT-TYPE
    SYNTAX      DisplayString
    MAX-ACCESS  read-write
    STATUS      current
    DESCRIPTION
        "Configure WEP key 3. The number of
        characters required for each WEP key depends on how user sets
        'Key Length' and 'Key Type':

        - If Key Length is 40 bits and the Key Type is 'ASCII',
          then each WEP key must be 5 characters long.
        - If Key Length is 40 bits and Key Type is 'Hex',
          then each WEP key must be 10 characters long.
        - If Key Length is 104 bits and Key Type is 'ASCII',
          then each WEP Key must be 13 characters long.
        - If Key Length is 104 bits and Key Type is 'Hex',
          then each WEP Key must be 26 characters long."
    ::= { apWgBridgeDwstrmEntry 10 }

apWgBridgeDwstrmWepKey4 OBJECT-TYPE
    SYNTAX      DisplayString
    MAX-ACCESS  read-write
    STATUS      current
    DESCRIPTION
        "Configure WEP key 4. The number of
        characters required for each WEP key depends on how user sets
        'Key Length' and 'Key Type':

        - If Key Length is 40 bits and the Key Type is 'ASCII',
          then each WEP key must be 5 characters long.
        - If Key Length is 40 bits and Key Type is 'Hex',
          then each WEP key must be 10 characters long.
        - If Key Length is 104 bits and Key Type is 'ASCII',
          then each WEP Key must be 13 characters long.
        - If Key Length is 104 bits and Key Type is 'Hex',
          then each WEP Key must be 26 characters long."
    ::= { apWgBridgeDwstrmEntry 11 }


apWgBridgeDwstrmOpenSystemAuth OBJECT-TYPE
    SYNTAX      TruthValue
    MAX-ACCESS  read-write
    STATUS      current
    DESCRIPTION
        "Indicates whether Open System authentication is permitted.
	Only used when security is static-wep."
    DEFVAL      { true }        
    ::= { apWgBridgeDwstrmEntry 12 }

apWgBridgeDwstrmSharedKeyAuth OBJECT-TYPE
    SYNTAX      TruthValue
    MAX-ACCESS  read-write
    STATUS      current
    DESCRIPTION
        "Indicates whether Shared Key authentication is permitted.
	Only used when security is static-wep."
    DEFVAL      { false }        
    ::= { apWgBridgeDwstrmEntry 13 }

apWgBridgeDwstrmWpaCipherTkip OBJECT-TYPE
    SYNTAX      TruthValue
    MAX-ACCESS  read-write
    STATUS      current
    DESCRIPTION
        "Indicates whether Temporal Key Integral Protocol (TKIP)
        is permitted as a WPA cipher.  Only used when security is wpa-personal.
        apWgBridgeDwstrmWpaCipherCcmp must be 'true' to turn off (false) TKIP. "
    DEFVAL      { true }        
    ::= { apWgBridgeDwstrmEntry 14 }

apWgBridgeDwstrmWpaCipherCcmp OBJECT-TYPE
    SYNTAX      TruthValue
    MAX-ACCESS  read-write
    STATUS      current
    DESCRIPTION
        "Indicates whether CCMP is permitted as a WPA cipher.
	Only used when security is wpa-personal.
        apWgBridgeDwstrmWpaCipherTkip must be 'true' to turn off (false) CCMP. "
    DEFVAL      { true }        
    ::= { apWgBridgeDwstrmEntry 15 }

apWgBridgeDwstrmWpaAllowed OBJECT-TYPE
    SYNTAX      TruthValue
    MAX-ACCESS  read-write
    STATUS      current
    DESCRIPTION
        "Indicates whether WPA is allowed.  Only used when security is wpa-personal.
         apWgBridgeDwstrmWpa2Allowed must be 'true' to turn off (false) apWgBridgeDwstrmWpaAllowed. "
    DEFVAL      { true }        
    ::= { apWgBridgeDwstrmEntry 16 }

apWgBridgeDwstrmWpa2Allowed OBJECT-TYPE
    SYNTAX      TruthValue
    MAX-ACCESS  read-write
    STATUS      current
    DESCRIPTION
        "Indicates whether WPA2 is allowed.  Only used when security is wpa-personal.
         apWgBridgeDwstrmWpaAllowed must be 'true' to turn off (false) apWgBridgeDwstrmWpa2Allowed. "
    DEFVAL      { true }        
    ::= { apWgBridgeDwstrmEntry 17 }

apWgBridgeDwstrmVlanID	    OBJECT-TYPE
        SYNTAX          Integer32 (1..4094)
        MAX-ACCESS      read-write
        STATUS          current
        DESCRIPTION
                "VLAN ID associated with VAP."
        DEFVAL    { 1 }               
        ::= { apWgBridgeDwstrmEntry 18 }

apWgBridgeDwstrmStatus OBJECT-TYPE
    SYNTAX      INTEGER{
                        up(1),
                        down(2)
                }
    MAX-ACCESS  read-write
    STATUS      current
    DESCRIPTION
        "Indicates the status of the downstream interface."
    DEFVAL      { down }        
    ::= { apWgBridgeDwstrmEntry 19}

apWgBridgeDwstrmMacAclMode OBJECT-TYPE
    SYNTAX      INTEGER{
                denyList(1),
                acceptList(2)        
                }         
    MAX-ACCESS  read-write
    STATUS      current
    DESCRIPTION
            "Mode for the MAC access list."
    DEFVAL      { denyList }        
    ::= { apWgBridgeDwstrmEntry 20 }

apWgBridgeDwstrmMacAclName OBJECT-TYPE
    SYNTAX      DisplayString
    MAX-ACCESS  read-only
    STATUS      obsolete
    DESCRIPTION
            "MAC ACL name from the existing list of MAC ACL instances."
    ::= { apWgBridgeDwstrmEntry 21 }

apWgBridgeDwstrmIgnoreBcastSsid OBJECT-TYPE
    SYNTAX      TruthValue
    MAX-ACCESS  read-write
    STATUS      current
    DESCRIPTION
	"When true,  the SSID string is not included in beacons and broadcast probes are ignored."
    DEFVAL      { false }        
    ::= { apWgBridgeDwstrmEntry 22 }

apWgBridgeDwstrmBcastKeyRefreshRate	    OBJECT-TYPE
        SYNTAX          Integer32 (0..86400)
        MAX-ACCESS      read-write
        STATUS          current
        DESCRIPTION
	"Specifies the interval after which the broadcast keys
        are changed.  Only used when security is wpa-personal."
        DEFVAL    { 300 }               
        ::= { apWgBridgeDwstrmEntry 23}
apWgBridgeDwstrmRxBytes        OBJECT-TYPE
        SYNTAX           Integer32
        MAX-ACCESS       read-only
        STATUS           current
        DESCRIPTION
             "Indicates received bytes."
        ::= { apWgBridgeDwstrmEntry 24 }       

apWgBridgeDwstrmRxPackets      OBJECT-TYPE
        SYNTAX           Integer32
        MAX-ACCESS       read-only
        STATUS           current
        DESCRIPTION
        "Indicates received packets."
        ::= { apWgBridgeDwstrmEntry 25 } 

apWgBridgeDwstrmTxBytes        OBJECT-TYPE
        SYNTAX           Integer32
        MAX-ACCESS       read-only
        STATUS           current
        DESCRIPTION
             "Indicates transmitted bytes."
        ::= { apWgBridgeDwstrmEntry 26 }       

apWgBridgeDwstrmTxPackets      OBJECT-TYPE
        SYNTAX           Integer32
        MAX-ACCESS       read-only
        STATUS           current
        DESCRIPTION
             "Indicates transmitted packets."
        ::= { apWgBridgeDwstrmEntry 27 }
 
apWgBridgeDwstrmMacAclAuthType OBJECT-TYPE
    SYNTAX      INTEGER{
                disable(1),
                local(2),
                radius(3)
                }
    MAX-ACCESS  read-write
    STATUS      current
    DESCRIPTION
            "Type for the MAC access authentication."
    DEFVAL      { disable }
    ::= { apWgBridgeDwstrmEntry 28 }


--
-- conformance information
--
wlanAPMIBCompliance 
      OBJECT IDENTIFIER ::= { wlanAPConformance 1 }
wlanAPMIBGroup OBJECT IDENTIFIER ::= { wlanAPConformance 2 }

-- compliance statements
wlanAPMIBCompliance2 MODULE-COMPLIANCE
    STATUS     current
    DESCRIPTION "The compliance statement for the AP."

MODULE -- this module

GROUP wlanAPSysGroup
    DESCRIPTION "This group is mandatory for the AP Management." 

GROUP wlanAPGlobalGroup
    DESCRIPTION "This group is mandatory global parameters for the 
    AP Management." 

GROUP wlanAPLogEntryGroup
    DESCRIPTION "This group is mandatory Log Entries for the 
    AP Management." 

GROUP wlanAPVAPEntryGroup
    DESCRIPTION "This group is mandatory VAP Entries for the AP." 

GROUP wlanAPInterfaceEntryGroup
    DESCRIPTION "This group is mandatory Interface Entries for the AP." 

GROUP wlanAPRadioEntryGroup
    DESCRIPTION "This group is mandatory Radio Entries for the AP." 

GROUP wlanAPBssEntryGroup
    DESCRIPTION "The group of objects for BSS Entries of the AP." 

GROUP wlanAPAssociationEntryGroup
    DESCRIPTION "The group of objects for Association Entries 
                 of the AP." 

GROUP wlanAPDetectionEntryGroup
    DESCRIPTION "The group of objects for AP Detection Entries 
                 of the AP." 

GROUP wlanAPBasicRateEntryGroup
    DESCRIPTION "The group of objects for basic Rate Entries of the AP." 

GROUP wlanAPSupportedEntriesEntryGroup
    DESCRIPTION "The group of objects for supported rate Entries 
                 of the AP." 


::= { wlanAPMIBCompliance 2 }

-- units of conformance

wlanAPSysGroup OBJECT-GROUP OBJECTS   
   { apSysConfPasswd, apSysConfModel, apSysConfVersion, 
     apSysConfPlatform, apSysConfBaseMac,
     apSysConfSerialNumber, apSysConfMD5Checksum,
     i802SystemReboot, i802SystemPersistConfig, i802SystemFactoryReset,
     i802SystemActivateBackupImage }
    STATUS     current
    DESCRIPTION "The group of objects for basic management of the AP." 
    ::= { wlanAPMIBGroup 1 }


wlanAPGlobalGroup OBJECT-GROUP OBJECTS   
   { apSupplicantConfigStatus, apSupplicantConfigUser, 
     apSupplicantConfigPassword,
     apHostId, apHostDns1Addr, apHostDns1Type, apHostDns2Addr,
     apHostDns2Type, apHostDomain, apHostStatDns1Addr, 
     apHostStatDns1Type, apHostStatDns2Addr, apHostStatDns2Type, 
     apHostStatDomain, apHostDnsViaDhcp,
--IFDEF IPV6_MGMT DNSv6 Support
     apHostDnsipv61Addr, apHostDnsipv61Type, apHostDnsipv62Addr,
     apHostDnsipv62Type, apHostStatDnsipv61Addr, 
     apHostStatDnsipv61Type, apHostStatDnsipv62Addr, apHostStatDnsipv62Type, 
     apHostDnsViaDhcpv6,
--ENDIF DNSv6 Support 
     apMgmtAccTelnet, 
     apMgmtAccHttpsStatus, apMgmtAccHttpStatus, apMgmtAccHttpPort, 
     apMgmtAccNtp, apMgmtAccNtpAddr, apMgmtAccNtpAddrType,
     apMgmtAccACLMode, apMgmtAccACLIpAddr1Type, apMgmtAccACLIpAddr1,
     apMgmtAccACLIpAddr2Type, apMgmtAccACLIpAddr2, 
     apMgmtAccACLIpAddr3Type, apMgmtAccACLIpAddr3,
     apMgmtAccACLIpAddr4Type, apMgmtAccACLIpAddr4,
     apMgmtAccACLIpAddr5Type, apMgmtAccACLIpAddr5,
     apMgmtAccSsh, apMgmtAccGenSslCert, apMgmtAccSessionMax,
     apMgmtAccSessionTimeout, apManagementVlanID, 
     apManagementInterface, apManagementStaticipType, 
     apManagementStaticip, apManagementStaticMaskType,
     apManagementStaticMask, apManagementIPType,
     apManagementIP, apManagementMaskType, apManagementMask, 
     apManagementMAC, apManagementDhcpStatus, apUntaggedVlanID,
     apUntaggedVlanStatus, apGlobalRadiusAccMode, 
     apGlobalRadiusIPAddressType, apGlobalRadiusPrimaryServerIPAddress,
     apGlobalRadiusBackuponeServerIPAddressType, 
     apGlobalRadiusBackuponeServerIPAddress,
     apGlobalRadiusBackuptwoServerIPAddressType, 
     apGlobalRadiusBackuptwoServerIPAddress,
     apGlobalRadiusBackupthreeServerIPAddressType,
     apGlobalRadiusBackupthreeServerIPAddress,
     apGlobalRadiusPrimaryServerKey,
     apGlobalRadiusBackuponeServerKey,
     apGlobalRadiusBackuptwoServerKey,
     apGlobalRadiusBackupthreeServerKey,
     apStaticIpRouteDestType,apStaticIpRouteDest,
     apStaticIpRouteMaskType, apStaticIpRouteMask,
     apStaticIpRouteGatewayType, apStaticIpRouteGateway,
     apBridgeConfigStp, apBridgeConfigFd, apBridgeConfigHello,
     apFirmwareUpgradeAddress, apFirmwareUpgradeAddressType, 
     apFirmwareUpgradePort, apFirmwareUpgradeDirectory,
     apFirmwareDownloadImagename, apFirmwareUpgradeProtocol,
     apFirmwareUpgradeStart, apFirmwareImageDownloadStatus,
     apFileTransferProtocol, apFileTransferSrcFileType, apFileTransferDstFileType,
     apFileTransferFilename, apFileTransferAddressType,
     apFileTransferAddress, apFileTransferPort, 
     apFileTransferStart, apFileTransferStatus,
     apFileTransferValidationStatus,
     apLogDepth, apLogPersistence, apLogSeverity, apLogRelayEnabled,
     apLogRelayHostType, apLogRelayHost, apLogRelayPort }
    STATUS     current
    DESCRIPTION "The group of objects for Global Parameters of the AP." 
    ::= { wlanAPMIBGroup 2 }


wlanAPLogEntryGroup OBJECT-GROUP OBJECTS   
    { apLogEntryPriority, apLogEntryTime,
      apLogEntryDaemon, apLogEntryMessage }
    STATUS     current
    DESCRIPTION "The group of objects for Log Entries of the AP." 
    ::= { wlanAPMIBGroup 3 }

wlanAPVAPEntryGroup OBJECT-GROUP OBJECTS   
    { apVapStatus, apVapVlanID, apVapDescription}
    STATUS     current
    DESCRIPTION "The group of objects for VAP Entries of the AP." 
    ::= { wlanAPMIBGroup 4 }


wlanAPInterfaceEntryGroup OBJECT-GROUP OBJECTS
    { apIfConfigName, apIfConfigType, apIfConfigMacAddress,
      apIfConfigStaticIpType, apIfConfigStaticIp,
      apIfConfigStaticMaskType, apIfConfigStaticMask,
      apIfConfigPathcost, apIfConfigPriority, apIfConfigSsid,
      apIfConfigBss, apIfConfigSecurity, apIfConfigWpaPersonalKey,
      apIfConfigWepKeyAscii, apIfConfigWepKeyLength,
      apIfConfigWepDefaultKey, apIfConfigWepKey1, apIfConfigWepKey2,
      apIfConfigWepKey3, apIfConfigWepKey4, apIfConfigRadio, 
      apIfConfigRemoteMac, apIfConfigWepKey, apIfConfigWdsSsid,
      apIfConfigWdsSecPolicy, apIfConfigWdsWpaPskKey, apIfConfigRxBytes,
      apIfConfigTxBytes, apIfConfigRxPackets, apIfConfigTxPackets,
      apIfConfigRxErrors, apIfConfigTxErrors, apIfConfigTxDropBytes,
      apIfConfigRxDropBytes, apIfConfigTxDropPackets, 
      apIfConfigRxDropPackets, apIfConfigTsVoTxBytes,apIfConfigTsViTxBytes,
      apIfConfigTsVoRxBytes,apIfConfigTsViRxBytes,apIfConfigTsVoTxPackets,
      apIfConfigTsViTxPackets,
      apIfConfigTsVoRxPackets,apIfConfigTsViRxPackets,apIfConfigGreenEthMode }
    STATUS     current
    DESCRIPTION "The group of objects for Interface Entries of the AP." 
    ::= { wlanAPMIBGroup 5 }


wlanAPRadioEntryGroup OBJECT-GROUP OBJECTS
    { apRadioStatus, apRadioName, apRadioMac, apRadioMaxBss,
      apRadioChannelPolicy, apRadioMode, apRadioDot11h,
      apRadioDot11d, apRadioStaticChannel, apRadioChannel,
      apRadioTxPower, apRadioBeaconInterval, apRadioRtsThreshold, 
      apRadioFragThreshold, apRadioApDetection,
      apRadioFrequency, apRadioWme, apRadioWmeNoAck, apRadioWmeAPSD, 
      apRadioRateLimitEnable, apRadioRateLimit, apRadioRateLimitBurst,
      apRadioWlanUtil, apRadioChannelBandwidth, apRadioPrimaryChannel,
      apRadioShortGuardIntervalSupported, apRadioProtection, 
      apRadioFixedMulticastRate,apRadioDtimPeriod, apRadioMaxStations,
      apRadioEdcaTemplate} 
    STATUS     current
    DESCRIPTION "The group of objects for Radio Entries of the AP." 
    ::= { wlanAPMIBGroup 6 }

wlanAPBssEntryGroup OBJECT-GROUP OBJECTS
    { apBssStatus, apBssDescr, apBssRadio, apBssBeaconInterface,
      apBssMac, apBssIgnoreBcastSsid,
      apBssMacAclMode, apBssMacAclName, apBssRadiusAccounting,
      apBssRadiusIpType, apBssRadiusPrimaryServerIp,
      apBssRadiusBackuponeServerIpType, apBssRadiusBackuponeServerIp,
      apBssRadiusBackuptwoServerIpType, apBssRadiusBackuptwoServerIp,
      apBssRadiusBackupthreeServerIpType, 
      apBssRadiusBackupthreeServerIp, apBssRadiusCurrentServer,
      apBssRadiusPrimaryServerKey, apBssRadiusBackuponeServerKey,
      apBssRadiusBackuptwoServerKey, apBssRadiusBackupthreeServerKey,
      apBssOpenSystemAuth, apBssSharedKeyAuth,
      apBssWpaCipherTkip, apBssWpaCipherCcmp, apBssWpaAllowed,
      apBssWpa2Allowed, apBssRsnPreauth, apBssBroadcastKeyRefreshRate,
      apBssSessionKeyRefreshRate,apBssGlobalRadiusMode,apBssMacAclAuthType,apBssStationIsolation }  
    STATUS     current
    DESCRIPTION "The group of objects for BSS Entries of the AP." 
    ::= { wlanAPMIBGroup 7 }

wlanAPAssociationEntryGroup OBJECT-GROUP OBJECTS
    { apAssocInterface, apAssocAuthenticated, apAssocAssociated,
      apAssocRxPackets, apAssocTxPackets, apAssocRxBytes,
      apAssocTxBytes, apAssocListenInterval, apAssocLastRssi,
      apAssocTxDropBytes, apAssocRxDropBytes, apAssocTxDropPackets,
      apAssocRxDropPackets }
    STATUS     current
    DESCRIPTION "The group of objects for Association Entries of the AP." 
    ::= { wlanAPMIBGroup 8 }


wlanAPDetectionEntryGroup OBJECT-GROUP OBJECTS
    { apDetectedApBeaconInterval,
      apDetectedApCapability, apDetectedApType, apDetectedApPrivacy,
      apDetectedApSsid, apDetectedApWpa, apDetectedApPhyType,
      apDetectedApBand, apDetectedApChannel, apDetectedApRate,
      apDetectedApSignal, apDetectedApErp, apDetectedApBeacons,
      apDetectedApLastBeacon, apDetectedApSupportedRates }
    STATUS     current
    DESCRIPTION "The group of objects for AP Detection Entries of the AP." 
    ::= { wlanAPMIBGroup 9 }


wlanAPBasicRateEntryGroup OBJECT-GROUP OBJECTS
    { apRadioBasicRateStatus }
    STATUS     current
    DESCRIPTION "The group of objects for basic Rate Entries of the AP." 
    ::= { wlanAPMIBGroup 10 }


wlanAPSupportedEntriesEntryGroup OBJECT-GROUP OBJECTS
    { apRadioSuppRateStatus }
    STATUS     current
    DESCRIPTION "The group of objects for supported rate Entries 
                 of the AP." 
    ::= { wlanAPMIBGroup 11 }

END
